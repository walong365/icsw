-- ********************************************************************************
-- ********************************************************************************
--
-- File         : mmblade.mib
-- Description  : IBM Management Module MIB for SNMP
-- By           : Joe Bolan, IBM
-- Version      : 1.1
-- Date         : March 4, 2003
--
--
-- Copyright (c) 2002-2004 IBM  All Rights Reserved.
-- ********************************************************************************
--
-- Contains MIB description for:
--   This MIB is to be used to provide configuration support and monitoring for the 
--   BladeCenter, BladeCenter T, BladeCenter H, and BladeCenter HT.
--
-- ********************************************************************************
-- ********************************************************************************
-- Revisions:
--  03/25/2002  LJI  Create new for blade servers based on old ibmrsaag.mib
--  03/04/2003       Fix compile errors found on SNMP Director Browser
--  12/04/2003  BN   Add user profiles to support SNMPv3
--  01/19/2004  BN   Add critVolt
--  01/23/2004  BN   Add LEDs for switch modules 
--  02/02/2004  BN   Add SNMPv3 enable/disable
--  02/17/2004  BN   Add MAC addresses support for blades and daughter cards
--  03/05/2004  BN   Add firmware update for switch, MM, and blades
--  03/11/2004  BN   Change texts and remove references to MM under processorblade
--                   section
--  03/22/2004  BN   Change write-only to read-write on some MIBs
--  03/25/2004  PTN  Add 4.9.3.4.2 and 4.9.3.4.3
--  04/01/2004  BN   Add text about duplicate ID to remoteAccessIdEntryUserId
--  04/09/2004  BN   Add DNS option for LDAP
--  04/25/2004  PTN  Add 4.9.3.4.5  
--  04/03/2004  BN   Add main application 2 vpd for switch module
--  05/13/2004  BN   Add notes to BladeCenter and BladeCenter T specific MIBs
--  05/13/2004  BN   Add power management / fuel gauge
--  05/24/2004  BN   Remove underscore (_) in MIB name
--  06/17/2004  BN   Top Level OID for Testing only
--  06/18/2004  BN   Infiniband Switch support
--  07/06/2004  BN   Correct range for OCTET STRING for IBM Director
--  07/12/2004  BN   Add duty cycles
--  08/02/2004  MR   Add voltages and temperatures for IPMI blades
--  08/18/2004  TDM  Add additional powerRestart options for JS20 blade
--  09/01/2004  BN   Add displayBladeSELEntry
--  09/15/2004  MR   Add switch module health state
--  09/17/2004  BN   Add numeric value before text in response message for fuelGaugeStatus
--  09/27/2004  MR   Add iscsi options to boot path
--  10/04/2004  BN   Remove displayBladeSELEntry
--  10/13/2004  MD   Add OEM folder for telcoManagement
--  11/17/2004  MR   Add power module health state table and blower state
--  03/31/2005  BN   Fix Ping
--  04/27/2005  NL   Add Role table and Scope table for new user permissions
--  04/28/2005  BN   Document Front Panel Information LED and Blade Information LED
--                      can be powered off only 
--  05/19/2005  KS   Changed warnPowerManagement to systemPowerManagement and warnBladeThrottling
--                   to systemBladeThrottling.  These are now system level events instead of
--                   warnings.
--  05/20/2005  BN   Change ibmDirectorOverLAN(3) to ibmDiretorOverLAN(8)
--  05/24/2005  CJ   Add the other 3&4 Blowers' state and speed for BladeCenter T
--  05/31/2005  BN   Remove allowModemLogin, add remoteAlertEntryDelay, and correct remoteAlertRetryDelay
--  06/21/2005  BN   Correct BIST results
--  06/23/2005  DH   Move the ipmiManagement and ipmiEnabled object from the blaceCenter tree to 
--                   configureSP tree with index ....20
--  07/15/2005  NL   Remove iscsi options from boot path
--  09/21/2005  BN   Add Write access to bladeCenterVPD
--  09/28/2005  TGF  Add  bladeHardwareVpdMachineModel
--  10/08/2005  CSTL Add SNMP modification due to 1400W support
--  10/14/2005  JY   Put iscsi options back to boot path for IBM builds
--  10/26/2005  CSTL Add comments to the description of snmpCommunityEntryCommunityName and snmpCommunityEntryCommunityIpAddress1
--  10/26/2005  CSTL Modifications to remoteControlBladePowerState and remoteControlBladeHealthState
--  10/27/2005  CSTL Change MAC Address size from 6 to 17 for OCTET STRING type
--  10/27/2005  TGF  Change diabled to disabled
--  10/28/2005  CSTL Add notes in snmpUserProfileEntryContextName description
--  11/03/2005  BN   Correct names
--  11/14/2005  CSTL Add notes to smNewIPAddr, smNewSubnetMask, smNewGateway and smNewIPConfigMethod.
--  01/23/2006  CSTL Modify bladeDaughterVpdCardType and componentLevelVpdTypeCode
--  02/08/2006  BN   Context name can be duplicate 
--  02/16/2005  DH   Add hardDrive4 in bootSequence
--  08/18/2006  CSTL Add the spTxtID desrciption
-- ********************************************************************************
        BLADE-MIB DEFINITIONS ::= BEGIN


        IMPORTS
            OBJECT-TYPE                          FROM RFC-1212
            enterprises                          FROM RFC1155-SMI
            -- DisplayString                        FROM RFC1213-MIB
            IpAddress                            FROM RFC1155-SMI
            TRAP-TYPE                            FROM RFC-1215;

        -- IBM enterprise group
        ibm         OBJECT IDENTIFIER ::=   { enterprises 2 }

        -- IBM products group
        ibmAgents      OBJECT IDENTIFIER ::=   { ibm 3 }

        -- IBM Advanced System Management Support Processor (SP) agent group
        netfinitySupportProcessorAgent OBJECT IDENTIFIER ::= { ibmAgents 51 }

        -- IBM BladeCenter Management Module (MM)
        -- Also known as Advanced System Mangement(ASM) or Support Processor (SP)
        bladeCenterSnmpMIB     OBJECT IDENTIFIER ::= { netfinitySupportProcessorAgent 2 }

-- ********************************************************************************
-- Start: Define groups of objects within the bladeCenterSnmpMIB
-- ********************************************************************************
  -- This group of objects provides the various environmental monitors for the
  -- local system and the MM
  -- 2
  monitors OBJECT IDENTIFIER ::= { bladeCenterSnmpMIB 2 }

  -- This group of objects provides the error log objects for the MM
  -- 3
  errorLogs OBJECT IDENTIFIER ::= { bladeCenterSnmpMIB 3 }

  -- This group of objects provides configuration functions for the MM
  -- 4
  configureSP     OBJECT IDENTIFIER ::= { bladeCenterSnmpMIB 4 }

  -- This group of objects provides system management functions for BladeCenter T
  -- 5
  telcoManagement  OBJECT IDENTIFIER ::= { bladeCenterSnmpMIB 5 }

  -- This group of objects provides configuration functions for system power
  -- 6
--  systemPower  OBJECT IDENTIFIER ::= { bladeCenterSnmpMIB 6 }

  -- This group of objects provides functions to boot the MM and system
  -- 7
  restartReset      OBJECT IDENTIFIER ::= { bladeCenterSnmpMIB 7 }

  -- This group of objects provides information specific to blades
  -- 22
  bladeCenter OBJECT IDENTIFIER ::= { bladeCenterSnmpMIB 22 }

  -- This group of objects provides information on the PCI-X expansion enclosure
  -- 21
  -- pcixExpansionBox      OBJECT IDENTIFIER ::= { bladeCenterSnmpMIB 21 }

    -- ********************************************************************************
    -- Temperature
    -- ********************************************************************************
    -- 2.1
    temperature OBJECT IDENTIFIER ::= { monitors 1 }

     -- Planar Temperature
     -- 2.1.1
     planarTemp OBJECT IDENTIFIER ::= { temperature 1 }

       -- 2.1.1.2? renamed
      mmTemp      OBJECT-TYPE
                   SYNTAX  OCTET STRING
                   ACCESS  read-only
                   STATUS  mandatory
                   DESCRIPTION
                   "Management module temperature in degrees centigrade(C).
                   An octet string expressed as 'sddd.dd Centigrade' where:
                   s is the sign ('-' for negative or blank space for positive)
                   d is a decimal digit or blank space for leading zeroes.
                   The string 'Not Readable!' indicates that the given monitor
                   is not supported on this system."
                   ::= { planarTemp 2 }


     -- CPUx Temperature
     -- 2.1.2
     cpuXTemp OBJECT IDENTIFIER ::= { temperature 2 }

     -- System Ambient Temperature
     -- 2.1.5
     ambientTemp OBJECT IDENTIFIER ::= { temperature 5 }

      -- 2.1.5.1 renamed
      frontPanelTemp    OBJECT-TYPE
                   SYNTAX  OCTET STRING
                   ACCESS  read-only
                   STATUS  mandatory
                   DESCRIPTION
                   "The front panel temperature in degrees centigrade(C).
                   This is surrounding temperature where the system is installed.
                   An octet string expressed as 'sddd.dd Centigrade' where:
                   s is the sign ('-' for negative or blank space for positive)
                   d is a decimal digit or blank space for a leading zero.
                   The string 'Not Readable!' indicates that the given monitor
                   is not supported on this system."
                   ::= { ambientTemp 1 }

    -- ********************************************************************************
    -- Voltages
    -- ********************************************************************************
    -- 2.2
    voltage OBJECT IDENTIFIER ::= { monitors 2 }

     -- Planar Voltages
     -- 2.2.1
     planarVolt OBJECT IDENTIFIER ::= { voltage 1 }

      -- 2.2.1.1
      plus5Volt     OBJECT-TYPE
                   SYNTAX  OCTET STRING
                   ACCESS  read-only
                   STATUS  mandatory
                   DESCRIPTION
                   "+5 Volt power supply voltage reading expressed in Volts(V).
                   An octet string expressed as 'sdd.dd Volts' where:
                   s is the sign ('-' for negative or '+' for positive)
                   d is a decimal digit or blank space for a leading zero.
                   The string 'Not Readable!' indicates that the given monitor
                   is not supported on this system."
                   ::= { planarVolt 1 }

      -- 2.2.1.2  renamed
      plus3Pt3Volt     OBJECT-TYPE
                   SYNTAX  OCTET STRING
                   ACCESS  read-only
                   STATUS  mandatory
                   DESCRIPTION
                   "+3.3 Volt power supply voltage reading expressed in Volts(V).
                   An octet string expressed as 'sdd.dd Volts' where:
                   s is the sign ('-' for negative or '+' for positive)
                   d is a decimal digit or blank space for a leading zero.
                   The string 'Not Readable!' indicates that the given monitor
                   is not supported on this system."
                   ::= { planarVolt 2 }

      -- 2.2.1.3
      plus12Volt    OBJECT-TYPE
                   SYNTAX  OCTET STRING
                   ACCESS  read-only
                   STATUS  mandatory
                   DESCRIPTION
                   "+12 Volt power supply voltage reading expressed in Volts(V).
                   An octet string expressed as 'sdd.dd Volts' where:
                   s is the sign ('-' for negative or '+' for positive)
                   d is a decimal digit or blank space for a leading zero.
                   The string 'Not Readable!' indicates that the given monitor
                   is not supported on this system."
                   ::= { planarVolt 3 }

      -- 2.2.1.4
--    minus12Volt    OBJECT-TYPE
--                 SYNTAX  OCTET STRING
--                 ACCESS  read-only
--                 STATUS  mandatory
--                 DESCRIPTION
--                 "-12 Volt power supply voltage reading expressed in Volts(V).
--                 An octet string expressed as 'sdd.dd Volts' where:
--                 s is the sign ('-' for negative or '+' for positive)
--                 d is a decimal digit or blank space for a leading zero.
--                 The string 'Not Readable!' indicates that the given monitor
--                 is not supported on this system."
--                 ::= { planarVolt 4 }

      -- 2.2.1.1
      minus5Volt     OBJECT-TYPE
                   SYNTAX  OCTET STRING
                   ACCESS  read-only
                   STATUS  mandatory
                   DESCRIPTION
                   "-5 Volt power supply voltage reading expressed in Volts(V).
                   An octet string expressed as 'sdd.dd Volts' where:
                   s is the sign ('-' for negative or '+' for positive)
                   d is a decimal digit or blank space for a leading zero.
                   The string 'Not Readable!' indicates that the given monitor
                   is not supported on this system."
                   ::= { planarVolt 5 }

      -- 2.2.1.6
      plus2Pt5Volt  OBJECT-TYPE
                   SYNTAX  OCTET STRING
                   ACCESS  read-only
                   STATUS  mandatory
                   DESCRIPTION
                   "+2.5 Volt power supply voltage reading expressed in Volts(V).
                   An octet string expressed as 'sdd.dd Volts' where:
                   s is the sign ('-' for negative or '+' for positive)
                   d is a decimal digit or blank space for a leading zero.
                   The string 'Not Readable!' indicates that the given monitor
                   is not supported on this system."
                   ::= { planarVolt 6 }

      -- 2.2.1.7
--    plus1Pt5Volt  OBJECT-TYPE
--                 SYNTAX  OCTET STRING
--                 ACCESS  read-only
--                 STATUS  mandatory
--                 DESCRIPTION
--                 "+1.5 Volt power supply voltage reading expressed in Volts(V).
--                 An octet string expressed as 'sdd.dd Volts' where:
--                 s is the sign ('-' for negative or '+' for positive)
--                 d is a decimal digit or blank space for a leading zero.
--                 The string 'Not Readable!' indicates that the given monitor
--                 is not supported on this system."
--                 ::= { planarVolt 7 }

      -- 2.2.1.8
      plus1Pt8Volt  OBJECT-TYPE
                   SYNTAX  OCTET STRING
                   ACCESS  read-only
                   STATUS  mandatory
                   DESCRIPTION
                   "+1.8 Volt power supply voltage reading expressed in Volts(V).
                   An octet string expressed as 'sdd.dd Volts' where:
                   s is the sign ('-' for negative or '+' for positive)
                   d is a decimal digit or blank space for a leading zero.
                   The string 'Not Readable!' indicates that the given monitor
                   is not supported on this system."
                   ::= { planarVolt 8 }

      -- 2.2.1.13
--    plus1Pt25Volt  OBJECT-TYPE
--                 SYNTAX  OCTET STRING
--                 ACCESS  read-only
--                 STATUS  mandatory
--                 DESCRIPTION
--                 "+1.25 Volt power supply voltage reading expressed in Volts(V).
--                 An octet string expressed as 'sdd.dd Volts' where:
--                 s is the sign ('-' for negative or '+' for positive)
--                 d is a decimal digit or blank space for a leading zero.
--                 The string 'Not Readable!' indicates that the given monitor
--                 is not supported on this system."
--                 ::= { planarVolt 13 }
--
     -- Voltage Regulator Module Voltages
     -- 2.2.3
--   vrmVolt OBJECT IDENTIFIER ::= { voltage 3 }
--
      -- 2.2.3.1
--    vrm1Volt     OBJECT-TYPE
--                 SYNTAX  OCTET STRING
--                 ACCESS  read-only
--                 STATUS  mandatory
--                 DESCRIPTION
--                 "VRM 1 voltage reading expressed in Volts(V).
--                 An octet string expressed as 'sdd.dd Volts' where:
--                 s is the sign ('-' for negative or '+' for positive)
--                 d is a decimal digit or blank space for a leading zero.
--                 The string 'Not Readable!' indicates that the given monitor
--                 is not supported on this system."
--                 ::= { vrmVolt 1 }

    -- ********************************************************************************
    -- Blowers
    -- ********************************************************************************
    -- 2.3
    blowers OBJECT IDENTIFIER ::= { monitors 3 }

     -- 2.3.1
     blower1speed    OBJECT-TYPE
                  SYNTAX  OCTET STRING
                  ACCESS  read-only
                  STATUS  mandatory
                  DESCRIPTION
                  "Blower 1 speed expressed in percent(%) of maximum RPM.
                  An octet string expressed as 'ddd% of maximum' where:
                  d is a decimal digit or blank space for a leading zero.
                  If the blower is determined not to be running or
                  the blower speed cannot be determined, the string will
                  indicate 'Offline'.
                  The string 'Not Readable!' indicates that the given monitor
                  is not supported on this system."
                  ::= { blowers 1 }

     -- 2.3.2
     blower2speed    OBJECT-TYPE
                  SYNTAX  OCTET STRING
                  ACCESS  read-only
                  STATUS  mandatory
                  DESCRIPTION
                  "Blower 2 speed expressed in percent(%) of maximum RPM.
                  An octet string expressed as 'ddd% of maximum' where:
                  d is a decimal digit or blank space for a leading zero.
                  If the blower is determined not to be running or
                  the blower speed cannot be determined, the string will
                  indicate 'Offline'.
                  The string 'Not Readable!' indicates that the given monitor
                  is not supported on this system."
                  ::= { blowers 2 }
                  
     -- 2.3.3
     blower3speed    OBJECT-TYPE
                  SYNTAX  OCTET STRING
                  ACCESS  read-only
                  STATUS  mandatory
                  DESCRIPTION
                  "Blower 3 speed expressed in percent(%) of maximum RPM.
                  An octet string expressed as 'ddd% of maximum' where:
                  d is a decimal digit or blank space for a leading zero.
                  If the blower is determined not to be running or
                  the blower speed cannot be determined, the string will
                  indicate 'Offline'.
                  The string 'Not Readable!' indicates that the given monitor
                  is not supported on this system."
                  ::= { blowers 3 }

     -- 2.3.4
     blower4speed    OBJECT-TYPE
                  SYNTAX  OCTET STRING
                  ACCESS  read-only
                  STATUS  mandatory
                  DESCRIPTION
                  "Blower 4 speed expressed in percent(%) of maximum RPM.
                  An octet string expressed as 'ddd% of maximum' where:
                  d is a decimal digit or blank space for a leading zero.
                  If the blower is determined not to be running or
                  the blower speed cannot be determined, the string will
                  indicate 'Offline'.
                  The string 'Not Readable!' indicates that the given monitor
                  is not supported on this system."
                  ::= { blowers 4 }
                  
     -- 2.3.10
     blower1State    OBJECT-TYPE
                   SYNTAX  INTEGER {
                     unknown(0),
                     good(1),
                     warning(2),
                     bad(3)
                   }
                   ACCESS  read-only
                   STATUS  mandatory
                   DESCRIPTION
                   "The health state for blower 1.
                   0 = unknown, 1 = good, 2 = warning, 3 = bad."
                   ::= { blowers 10}
                   
     -- 2.3.11
     blower2State    OBJECT-TYPE
                   SYNTAX  INTEGER {
                     unknown(0),
                     good(1),
                     warning(2),
                     bad(3)
                   }
                   ACCESS  read-only
                   STATUS  mandatory
                   DESCRIPTION
                   "The health state for blower 2.
                   0 = unknown, 1 = good, 2 = warning, 3 = bad."
                   ::= { blowers 11}
     -- 2.3.12
     blower3State    OBJECT-TYPE
                   SYNTAX  INTEGER {
                     unknown(0),
                     good(1),
                     warning(2),
                     bad(3)
                   }
                   ACCESS  read-only
                   STATUS  mandatory
                   DESCRIPTION
                   "The health state for blower 3.
                   0 = unknown, 1 = good, 2 = warning, 3 = bad."
                   ::= { blowers 12}
                   
     -- 2.3.13
     blower4State    OBJECT-TYPE
                   SYNTAX  INTEGER {
                     unknown(0),
                     good(1),
                     warning(2),
                     bad(3)
                   }
                   ACCESS  read-only
                   STATUS  mandatory
                   DESCRIPTION
                   "The health state for blower 4.
                   0 = unknown, 1 = good, 2 = warning, 3 = bad."
                   ::= { blowers 13}
                   
    -- ********************************************************************************
    -- Power Module Health State
    -- ********************************************************************************
    -- 2.4
    powerModuleHealth OBJECT IDENTIFIER ::= { monitors 4 }
    
      -- 2.4.1
      powerModuleHealthTable OBJECT-TYPE
                     SYNTAX  SEQUENCE OF PowerModuleHealthEntry
                     ACCESS  not-accessible
                     STATUS  mandatory
                     DESCRIPTION
                     "Table of power module health information.  Contains
                     the power health information for each power module."
                     ::= { powerModuleHealth 1 }

       powerModuleHealthEntry OBJECT-TYPE
                     SYNTAX PowerModuleHealthEntry
                     ACCESS  not-accessible
                     STATUS  mandatory
                     DESCRIPTION
                     "Power Module health entry"
                     INDEX { powerModuleIndex }
                     ::= { powerModuleHealthTable 1 }


       PowerModuleHealthEntry ::= SEQUENCE {
                   powerModuleIndex INTEGER,
                   powerModuleExists INTEGER,
                   powerModuleState INTEGER,
                   powerModuleDetails OCTET STRING
       }

       powerModuleIndex  OBJECT-TYPE
                   SYNTAX  INTEGER
                   ACCESS  read-only
                   STATUS  mandatory
                   DESCRIPTION
                   "Power module sequence index."
                   ::= { powerModuleHealthEntry 1 }
                   
       powerModuleExists OBJECT-TYPE
                   SYNTAX  INTEGER {
                     false(0),
                     true(1)
                   }
                   ACCESS  read-only
                   STATUS  mandatory
                   DESCRIPTION
                   "Indicates whether the power module specified exists or not."
                   ::= { powerModuleHealthEntry 2 }

       powerModuleState OBJECT-TYPE
                   SYNTAX  INTEGER {
                     unknown(0),
                     good(1),
                     warning(2),
                     notAvailable(3)
                   }
                   ACCESS  read-only
                   STATUS  mandatory
                   DESCRIPTION
                   "The health state for the power module.
                   0 = unknown, 1 = good, 2 = warning, 3 = not available."
                   ::= { powerModuleHealthEntry 3}

       powerModuleDetails OBJECT-TYPE
                   SYNTAX  OCTET STRING 
                   ACCESS  read-only
                   STATUS  mandatory
                   DESCRIPTION
                   "The details for this power module."
                   ::= { powerModuleHealthEntry 4 }

    -- ********************************************************************************
    -- MM Status
    -- ********************************************************************************
    -- 2.5
    spStatus OBJECT IDENTIFIER ::= { monitors 5 }

     -- 2.5.2.1
     mmBistAndChassisStatus OBJECT IDENTIFIER ::= { spStatus 2 }


      bistSdram  OBJECT-TYPE
                  SYNTAX  INTEGER {
                    testSucceeded(0),
                    testFailed(1)
                  }
                  ACCESS  read-only
                  STATUS  mandatory
                  DESCRIPTION
                  "MM BIST SDRAM test result."
                  ::= { mmBistAndChassisStatus 1 }

      bistRs485Port1 OBJECT-TYPE
                  SYNTAX  INTEGER {
                    testSucceeded(0),
                    testFailed(1)
                  }
                  ACCESS  read-only
                  STATUS  mandatory
                  DESCRIPTION
                  "MM BIST RS 485 legacy test result."
                  ::= { mmBistAndChassisStatus 2 }

      bistRs485Port2 OBJECT-TYPE
                  SYNTAX  INTEGER {
                    testSucceeded(0),
                    testFailed(1)
                  }
                  ACCESS  read-only
                  STATUS  mandatory
                  DESCRIPTION
                  "MM BIST RS 485 local bus test result."
                  ::= { mmBistAndChassisStatus 3 }

      bistNvram  OBJECT-TYPE
                  SYNTAX  INTEGER {
                    testSucceeded(0),
                    testFailed(1)
                  }
                  ACCESS  read-only
                  STATUS  mandatory
                  DESCRIPTION
                  "MM BIST NVRAM test result."
                  ::= { mmBistAndChassisStatus 4 }

      bistRtc OBJECT-TYPE
                  SYNTAX  INTEGER {
                    testSucceeded(0),
                    testFailed(1)
                  }
                  ACCESS  read-only
                  STATUS  mandatory
                  DESCRIPTION
                  "MM BIST Real Time Clock test result."
                  ::= { mmBistAndChassisStatus 5 }

      bistLocalI2CBus OBJECT-TYPE
                  SYNTAX  INTEGER {
                    testSucceeded(0),
                    testFailed(1)
                  }
                  ACCESS  read-only
                  STATUS  mandatory
                  DESCRIPTION
                  "MM BIST I2C controller test result."
                  ::= { mmBistAndChassisStatus 7 }

      bistPrimaryMainAppFlashImage  OBJECT-TYPE
                  SYNTAX  INTEGER {
                    testSucceeded(0),
                    testFailed(1)
                  }
                  ACCESS  read-only
                  STATUS  mandatory
                  DESCRIPTION
                  "MM BIST Com 2test result."
                  ::= { mmBistAndChassisStatus 8 }

      bistSecondaryMainAppFlashImage  OBJECT-TYPE
                  SYNTAX  INTEGER {
                    testSucceeded(0),
                    testFailed(1)
                  }
                  ACCESS  read-only
                  STATUS  mandatory
                  DESCRIPTION
                  "MM BIST Com 2test result."
                  ::= { mmBistAndChassisStatus 9 }

      bistBootRomFlashImage  OBJECT-TYPE
                  SYNTAX  INTEGER {
                    testSucceeded(0),
                    testFailed(1)
                  }
                  ACCESS  read-only
                  STATUS  mandatory
                  DESCRIPTION
                  "MM BIST Com 2test result."
                  ::= { mmBistAndChassisStatus 10 }

      bistEthernetPort1 OBJECT-TYPE
                  SYNTAX  INTEGER {
                    testSucceeded(0),
                    testFailed(1)
                  }
                  ACCESS  read-only
                  STATUS  mandatory
                  DESCRIPTION
                  "MM BIST external ethernet - internal wrap test result."
                  ::= { mmBistAndChassisStatus 11 }

      bistEthernetPort2 OBJECT-TYPE
                  SYNTAX  INTEGER {
                    testSucceeded(0),
                    testFailed(1)
                  }
                  ACCESS  read-only
                  STATUS  mandatory
                  DESCRIPTION
                  "MM BIST external ethernet - external wrap test result."
                  ::= { mmBistAndChassisStatus 12 }

      bistInternalPCIBus OBJECT-TYPE
                  SYNTAX  INTEGER {
                    testSucceeded(0),
                    testFailed(1)
                  }
                  ACCESS  read-only
                  STATUS  mandatory
                  DESCRIPTION
                  "MM BIST I2C controller test result."
                  ::= { mmBistAndChassisStatus 13 }

      bistExternalI2CDevices OBJECT-TYPE
                  SYNTAX  INTEGER {
                    testSucceeded(0),
                    testFailed(1)
                  }
                  ACCESS  read-only
                  STATUS  mandatory
                  DESCRIPTION
                  "MM BIST I2C controller test result."
                  ::= { mmBistAndChassisStatus 14 }

      bistUSBController OBJECT-TYPE
                  SYNTAX  INTEGER {
                    testSucceeded(0),
                    testFailed(1)
                  }
                  ACCESS  read-only
                  STATUS  mandatory
                  DESCRIPTION
                  "MM BIST I2C controller test result."
                  ::= { mmBistAndChassisStatus 15 }

      bistVideoCompressorBoard OBJECT-TYPE
                  SYNTAX  INTEGER {
                    testSucceeded(0),
                    testFailed(1)
                  }
                  ACCESS  read-only
                  STATUS  mandatory
                  DESCRIPTION
                  "MM BIST I2C controller test result."
                  ::= { mmBistAndChassisStatus 16 }
      
      bistRemoteVideo OBJECT-TYPE
                  SYNTAX  INTEGER {
                    testSucceeded(0),
                    testFailed(1)
                  }
                  ACCESS  read-only
                  STATUS  mandatory
                  DESCRIPTION
                  "MM BIST Remote Video test result."
                  ::= { mmBistAndChassisStatus 17 }

      bistPrimaryBus OBJECT-TYPE
                  SYNTAX  INTEGER {
                    testSucceeded(0),
                    testFailed(1)
                  }
                  ACCESS  read-only
                  STATUS  mandatory
                  DESCRIPTION
                  "MM BIST I2C controller test result."
                  ::= { mmBistAndChassisStatus 18 }

      bistInternalEthernetSwitch OBJECT-TYPE
                  SYNTAX  INTEGER {
                    testSucceeded(0),
                    testFailed(1)
                  }
                  ACCESS  read-only
                  STATUS  mandatory
                  DESCRIPTION
                  "MM BIST I2C controller test result."
                  ::= { mmBistAndChassisStatus 19 }


      bistBladesInstalled OBJECT-TYPE
                  SYNTAX  OCTET STRING
                  ACCESS  read-only
                  STATUS  mandatory
                  DESCRIPTION
                  "The blades that are installed on the chassis.
                  The blades are listed as a bitmap.  The bitmap is a
                  string containing a list of 1's and 0's that is as long as
                  the number of blades supported.  If a blade is installed in a
                  bay, a 1 is present in the string in the position representing
                  the bay ID as read from left to right.  For example, if blades
                  are installed in bays 1, 5, and 13, and 14 blades are supported,
                  the string would look like '10001000000010'."
                  ::= { mmBistAndChassisStatus 33 }

      bistBladesCommunicating OBJECT-TYPE
                  SYNTAX  OCTET STRING
                  ACCESS  read-only
                  STATUS  mandatory
                  DESCRIPTION
                  "The blades that are communicating on the chassis.
                  The blades are listed as a bitmap.  The bitmap is a
                  string containing a list of 1's and 0's that is as long as
                  the number of blades supported.  If a blade installed in a
                  bay is communicating, a 1 is present in the string in the position
                  representing the bay ID as read from left to right.  For example,
                  if blades are communicating in bays 1, 5, and 13, and 14 blades
                  are supported, the string would look like '10001000000010'."
                  ::= { mmBistAndChassisStatus 49 }

      bistBlowersInstalled OBJECT-TYPE
                  SYNTAX  OCTET STRING
                  ACCESS  read-only
                  STATUS  mandatory
                  DESCRIPTION
                  "The blowers that are installed on the chassis.
                  The blowers are listed as a bitmap.  The bitmap is a
                  string containing a list of 1's and 0's that is as long as
                  the number of blowers supported.  If a blower is installed in a
                  bay, a 1 is present in the string in the position representing
                  the bay ID as read from left to right.  For example, if a blower
                  is installed in bay 1, and 2 blowers are supported, the string
                  would look like '10'."
                  ::= { mmBistAndChassisStatus 65 }

      bistBlowersFunctional OBJECT-TYPE
                  SYNTAX  OCTET STRING
                  ACCESS  read-only
                  STATUS  mandatory
                  DESCRIPTION
                  "The blowers installed on the chassis that are functional.
                  The blowers are listed as a bitmap.  The bitmap is a
                  string containing a list of 1's and 0's that is as long as
                  the number of blowers supported.  If a blower is installed and
                  functional in a bay, a 1 is present in the string in the position
                  representing the bay ID as read from left to right.  For example,
                  if a blower is installed and functional only in bay 1, and 2 blowers
                  are supported, the string would look like '10'."
                  ::= { mmBistAndChassisStatus 73 }

      bistMediaTrayInstalled OBJECT-TYPE
                  SYNTAX  INTEGER {
                    no(0),
                    yes(1)
                  }
                  ACCESS  read-only
                  STATUS  mandatory
                  DESCRIPTION
                  "Indicates whether a media tray is installed on the chassis."
                  ::= { mmBistAndChassisStatus 74 }

      bistMediaTrayCommunicating OBJECT-TYPE
                  SYNTAX  INTEGER {
                    no(0),
                    yes(1)
                  }
                  ACCESS  read-only
                  STATUS  mandatory
                  DESCRIPTION
                  "Indicates whether a media tray is communicating."
                  ::= { mmBistAndChassisStatus 75 }

      bistPowerModulesInstalled OBJECT-TYPE
                  SYNTAX  OCTET STRING
                  ACCESS  read-only
                  STATUS  mandatory
                  DESCRIPTION
                  "The power modules that are installed on the chassis.
                  The power modules are listed as a bitmap.  The bitmap is a
                  string containing a list of 1's and 0's that is as long as
                  the number of power modules supported.  If a power module is
                  installed in a bay, a 1 is present in the string in the position
                  representing the bay ID as read from left to right.  For example,
                  if power modules are installed in bays 1 and 3, and 4 power modules
                  are supported, the string would look like '1010'."
                  ::= { mmBistAndChassisStatus 81 }

      bistPowerModulesFunctional OBJECT-TYPE
                  SYNTAX  OCTET STRING
                  ACCESS  read-only
                  STATUS  mandatory
                  DESCRIPTION
                  "The power modules that are functional on the chassis.
                  The power modules are listed as a bitmap.  The bitmap is a
                  string containing a list of 1's and 0's that is as long as
                  the number of power modules supported.  If a power module is
                  installed and functioning in a bay, a 1 is present in the string
                  in the position representing the bay ID as read from left to right.
                  For example, if power modules are installed and functioning in bays
                  1 and 3, and 4 power modules are supported, the string would look
                  like '1010'."
                  ::= { mmBistAndChassisStatus 89 }

      bistSwitchModulesInstalled OBJECT-TYPE
                  SYNTAX  OCTET STRING
                  ACCESS  read-only
                  STATUS  mandatory
                  DESCRIPTION
                  "The switch modules that are installed on the chassis.
                  The switch modules are listed as a bitmap.  The bitmap is a
                  string containing a list of 1's and 0's that is as long as
                  the number of switch modules supported.  If a switch module is
                  installed in a bay, a 1 is present in the string in the position
                  representing the bay ID as read from left to right.  For example,
                  if switch modules are installed in bays 1 and 3, and 4 switch modules
                  are supported, the string would look like '1011'."
                  ::= { mmBistAndChassisStatus 97 }

      bistSwitchModulesCommunicating OBJECT-TYPE
                  SYNTAX  OCTET STRING
                  ACCESS  read-only
                  STATUS  mandatory
                  DESCRIPTION
                  "The switch modules that are communicating on the chassis.
                  The switch modules are listed as a bitmap.  The bitmap is a
                  string containing a list of 1's and 0's that is as long as
                  the number of switch modules supported.  If a switch module is
                  installed and functioning in a bay, a 1 is present in the string
                  in the position representing the bay ID as read from left to right.
                  For example, if switch modules are installed and functioning in bays
                  1 and 3, and 4 switch modules are supported, the string would look
                  like '1011'."
                  ::= { mmBistAndChassisStatus 113 }


    -- ********************************************************************************
    -- System Health
    -- ********************************************************************************
    -- 2.7
    systemHealth OBJECT IDENTIFIER ::= { monitors 7 }

     -- ********************************************************************************
     -- System Health Status
     -- ********************************************************************************
     -- 2.7.1
     systemHealthStat  OBJECT-TYPE
                  SYNTAX  INTEGER {
                                    critical(0),
                                    nonCritical(2),
                                    systemLevel(4),
                                    normal(255)
                                  }
                  ACCESS  read-only
                  STATUS  mandatory
                  DESCRIPTION
                  "Indicates status of system health for the
                  system in which the MM resides.
                  Value of 'critical' indicates a severe error has occurred
                  and the system may not be functioning. A value of
                  'nonCritical' indicates that a error has occurred but
                  the system is currently functioning properly.A value of
                  'systemLevel' indicates that a condition has occurred
                  that may change the state of the system in the future but currently
                  the system is working properly. A value of
                  'normal' indicates that the system is operating normally."
                  ::= { systemHealth 1 }

     -- ********************************************************************************
     -- System Health Summary
     -- ********************************************************************************
     -- 2.7.2
     systemHealthSummaryTable OBJECT-TYPE
                   SYNTAX  SEQUENCE OF SystemHealthSummaryEntry
                   ACCESS  not-accessible
                   STATUS  mandatory
                   DESCRIPTION
                   "Table of System Health summary. Contains more detailed
                   information about the reasons for the overall system
                   health status.
                   
                   NOTE: This MIB is for BladeCenter only."
                   ::= { systemHealth 2 }

     systemHealthSummaryEntry OBJECT-TYPE
                   SYNTAX SystemHealthSummaryEntry
                   ACCESS  not-accessible
                   STATUS  mandatory
                   DESCRIPTION
                   "System Health Summary entry
                   
                   NOTE: This MIB is for BladeCenter only."
                   INDEX { systemHealthSummaryIndex }
                   ::= { systemHealthSummaryTable 1 }


     SystemHealthSummaryEntry ::= SEQUENCE {
                 systemHealthSummaryIndex INTEGER,
                 systemHealthSummarySeverity OCTET STRING,
                 systemHealthSummaryDescription OCTET STRING
     }


     systemHealthSummaryIndex  OBJECT-TYPE
                 SYNTAX  INTEGER
                 ACCESS  read-only
                 STATUS  mandatory
                 DESCRIPTION
                 "System health summary index.
                 
                 NOTE: This MIB is for BladeCenter only."
                 ::= { systemHealthSummaryEntry 1 }

     systemHealthSummarySeverity  OBJECT-TYPE
                 SYNTAX  OCTET STRING
                 ACCESS  read-only
                 STATUS  mandatory
                 DESCRIPTION
                 "System health summary severity.
                 
                 NOTE: This MIB is for BladeCenter only."
                 ::= { systemHealthSummaryEntry 2 }

     systemHealthSummaryDescription  OBJECT-TYPE
                 SYNTAX  OCTET STRING
                 ACCESS  read-only
                 STATUS  mandatory
                 DESCRIPTION
                 "System health summary description.
                 
                 NOTE: This MIB is for BladeCenter only."
                 ::= { systemHealthSummaryEntry 3 }

     -- 2.7.3
--   serverBladeSystemHealthState OBJECT-TYPE
--                SYNTAX  INTEGER {
--                  good(1),
--                  noncritical(2),
--                  bad(3)
--                }
--                ACCESS  read-only
--                STATUS  mandatory
--                DESCRIPTION
--                "Represents blades, chassis, power supplies, management
--                modules, and switches.  1 = good, 2 = non-critical,
--                3 = bad.
--
--                NOTE: This MIB is for BladeCenter only."
--                ::= { systemHealth 3 }
--

    -- ********************************************************************************
    -- LEDs
    -- ********************************************************************************
    leds OBJECT IDENTIFIER ::= { monitors 8 }

     -- ********************************************************************************
     -- Front Panel LEDs
     -- ********************************************************************************
     frontPanelLEDs OBJECT IDENTIFIER ::= { leds 1 }


      systemErrorLED OBJECT-TYPE
                   SYNTAX INTEGER {
                     off(0),
                     on(1)
                   }
                   ACCESS  read-only
                   STATUS  mandatory
                   DESCRIPTION
                   "Indicates whether the front panel system error LED is on or off.
                   
                   NOTE: This MIB is for BladeCenter only."
                   ::= { frontPanelLEDs 1 }


      -- 3.4.8
      informationLED OBJECT-TYPE
                   SYNTAX INTEGER {
                     off(0),
                     on(1)
                   }
                   ACCESS  read-write
                   STATUS  mandatory
                   DESCRIPTION
                   "Indicates whether the front panel system information LED
                   is on or off.  For Write access, the LED can be powered 
                   off only
                   
                   NOTE: This MIB is for BladeCenter only."
                   ::= { frontPanelLEDs 2 }


      temperatureLED OBJECT-TYPE
                   SYNTAX INTEGER {
                     off(0),
                     on(1)
                   }
                   ACCESS  read-only
                   STATUS  mandatory
                   DESCRIPTION
                   "Indicates whether the front panel temperature LED is on or off.
                   
                   NOTE: This MIB is for BladeCenter only."
                   ::= { frontPanelLEDs 3 }


      -- 13.7
      identityLED OBJECT-TYPE
                   SYNTAX INTEGER {
                     off(0),
                     on(1),
                     blinking(2),
                     notAvailable(3)
                   }
                   ACCESS  read-write
                   STATUS  mandatory
                   DESCRIPTION
                   "Indicates whether the front panel identity LED is on or off.
                   
                   NOTE: This MIB is for BladeCenter only."
                   ::= { frontPanelLEDs 4 }


     -- ********************************************************************************
     -- Blade LEDs
     -- ********************************************************************************
     bladeLEDs OBJECT IDENTIFIER ::= { leds 2 }

      bladeLEDsTable OBJECT-TYPE
                    SYNTAX  SEQUENCE OF BladeLEDsEntry
                    ACCESS  not-accessible
                    STATUS  mandatory
                    DESCRIPTION
                    "Table of blade status information."
                    ::= { bladeLEDs 1 }

       bladeLEDsEntry OBJECT-TYPE
                     SYNTAX BladeLEDsEntry
                     ACCESS  not-accessible
                     STATUS  mandatory
                     DESCRIPTION
                     "Blade system status entry"
                     INDEX { bladeStatusIndex }
                     ::= { bladeLEDsTable 1 }


       BladeLEDsEntry ::= SEQUENCE {
                   ledBladeIndex INTEGER,
                   ledBladeId INTEGER,
                   ledBladeExists INTEGER,
                   ledBladePowerState INTEGER,
                   ledBladeHealthState INTEGER,
                   ledBladeName OCTET STRING,
                   ledBladeSystemError INTEGER,
                   ledBladeInformation INTEGER,
                   ledBladeKVM INTEGER,
                   ledBladeMediaTray INTEGER,
                   ledBladeIdentity INTEGER
       }


       ledBladeIndex OBJECT-TYPE
                   SYNTAX  INTEGER
                   ACCESS  read-only
                   STATUS  mandatory
                   DESCRIPTION
                   "Blade LED table index."
                   ::= { bladeLEDsEntry 1 }

       ledBladeId OBJECT-TYPE
                   SYNTAX  INTEGER {
                       blade1(1),
                       blade2(2),
                       blade3(3),
                       blade4(4),
                       blade5(5),
                       blade6(6),
                       blade7(7),
                       blade8(8),
                       blade9(9),
                       blade10(10),
                       blade11(11),
                       blade12(12),
                       blade13(13),
                       blade14(14)
                     }
                   ACCESS  read-only
                   STATUS  mandatory
                   DESCRIPTION
                   "The numeric blade ID."
                   ::= { bladeLEDsEntry 2 }

       ledBladeExists OBJECT-TYPE
                   SYNTAX  INTEGER {
                     false(0),
                     true(1)
                   }
                   ACCESS  read-only
                   STATUS  mandatory
                   DESCRIPTION
                   "Indicates whether the server blade specified exists or not."
                   ::= { bladeLEDsEntry 3 }

       ledBladePowerState  OBJECT-TYPE
                   SYNTAX  INTEGER {
                     off(0),
                     on(1)
                   }
                   ACCESS  read-only
                   STATUS  mandatory
                   DESCRIPTION
                   "Indicates whether the server blade specified is powered on or not."
                   ::= { bladeLEDsEntry 4 }

       ledBladeHealthState  OBJECT-TYPE
                   SYNTAX  INTEGER {
                     unknown(0),
                     good(1),
                     warning(2),
                     bad(3)
                   }
                   ACCESS  read-only
                   STATUS  mandatory
                   DESCRIPTION
                   "The system health state for the blade server.
                   1 = good, 2 = warning, 3 = bad."
                   ::= { bladeLEDsEntry 5 }

       ledBladeName OBJECT-TYPE
                   SYNTAX  OCTET STRING
                   ACCESS  read-only
                   STATUS  mandatory
                   DESCRIPTION
                   "The name of the blade as a null terminated string."
                   ::= { bladeLEDsEntry 6 }

       ledBladeSystemError  OBJECT-TYPE
                   SYNTAX  INTEGER {
                     off(0),
                     on(1)
                   }
                   ACCESS  read-only
                   STATUS  mandatory
                   DESCRIPTION
                   "Indicates whether the blade system error LED is on or off."
                   ::= { bladeLEDsEntry 7 }

       ledBladeInformation  OBJECT-TYPE
                   SYNTAX  INTEGER {
                     off(0),
                     on(1)
                   }
                   ACCESS  read-write
                   STATUS  mandatory
                   DESCRIPTION
                   "Indicates whether the blade information LED is on or off.  
                   For Write access, the LED can be powered off only."
                   ::= { bladeLEDsEntry 8 }

       ledBladeKVM  OBJECT-TYPE
                   SYNTAX  INTEGER {
                     off(0),
                     on(1),
                     blinking(2)
                   }
                   ACCESS  read-only
                   STATUS  mandatory
                   DESCRIPTION
                   "Indicates whether the blade KVM LED is on, off, or blinking."
                   ::= { bladeLEDsEntry 9 }

       ledBladeMediaTray  OBJECT-TYPE
                   SYNTAX  INTEGER {
                     off(0),
                     on(1),
                     blinking(2)
                   }
                   ACCESS  read-only
                   STATUS  mandatory
                   DESCRIPTION
                   "Indicates whether the blade media tray LED is on, off, or blinking."
                   ::= { bladeLEDsEntry 10 }

       ledBladeIdentity OBJECT-TYPE
                   SYNTAX  INTEGER {
                     off(0),
                     on(1),
                     blinking(2)
                   }
                   ACCESS  read-write
                   STATUS  mandatory
                   DESCRIPTION
                   "Indicates whether the blade identify LED is on, off, or blinking."
                   ::= { bladeLEDsEntry 11 }


     -- ***********************************************************************
     -- BladeCenter T Panel LEDs
     -- ***********************************************************************
     telcoPanelLEDs OBJECT IDENTIFIER ::= { leds 3 }


     -- 13.10.1  
     criticalLED OBJECT-TYPE
                   SYNTAX INTEGER {
                     off(0),
                     on(1)
                   }
                   ACCESS  read-only
                   STATUS  mandatory
                   DESCRIPTION
                   "Indicates whether the BladeCenter T Panel CRT (Critical) LED is on or off.
                   
                   NOTE: This MIB is for BladeCenter T only."
                   ::= { telcoPanelLEDs 1 }


     -- 13.10.2
     majorLED OBJECT-TYPE
                   SYNTAX INTEGER {
                     off(0),
                     on(1)
                   }
                   ACCESS  read-only
                   STATUS  mandatory
                   DESCRIPTION
                   "Indicates whether the BladeCenter T Panel MJR (Major) LED is on or off.
                   
                   NOTE: This MIB is for BladeCenter T only."
                   ::= { telcoPanelLEDs 2 }

     -- 13.10.3
     minorLED OBJECT-TYPE
                   SYNTAX INTEGER {
                     off(0),
                     on(1)
                   }
                   ACCESS  read-only
                   STATUS  mandatory
                   DESCRIPTION
                   "Indicates whether the BladeCenter T Panel MNR (Minor) LED is on or off.
                   
                   NOTE: This MIB is for BladeCenter T only."
                   ::= { telcoPanelLEDs 3 }


     -- 13.7
     telcoIdentityLED OBJECT-TYPE
                   SYNTAX INTEGER {
                     off(0),
                     on(1),
                     blinking(2),
                     notAvailable(3)
                   }
                   ACCESS  read-write
                   STATUS  mandatory
                   DESCRIPTION
                   "Indicates whether the BladeCenter T Panel identity LED is on or off.
                   
                   NOTE: This MIB is for BladeCenter T only."
                   ::= { telcoPanelLEDs 4 }
    
 
     -- 13.10.6
     telcoColorSel OBJECT-TYPE
                   SYNTAX INTEGER {
                     amber(0),
                     red(1)
                   }
                   ACCESS  read-write
                   STATUS  mandatory
                   DESCRIPTION
                   "Indicates whether the BladeCenter T Critical and Major LEDs are displayed in amber or red color.
                   
                   NOTE: This MIB is for BladeCenter T only."
                   ::= { telcoPanelLEDs 5 }



     -- 13.10.7
     criticalityAssertionMode OBJECT-TYPE
                   SYNTAX INTEGER {
                     disable(0),
                     enable(1)
                   }
                   ACCESS  read-write
                   STATUS  mandatory
                   DESCRIPTION
                   "Indicates whether the BladeCenter T Criticality Assertion Mode is enable or disable.
                   
                   NOTE: This MIB is for BladeCenter T only."
                   ::= { telcoPanelLEDs 6 }



     -- ********************************************************************************
     -- Switch Module LEDs
     -- ********************************************************************************
     smLEDs OBJECT IDENTIFIER ::= { leds 4 }

      smLEDsTable OBJECT-TYPE
                    SYNTAX  SEQUENCE OF SMLEDsEntry
                    ACCESS  not-accessible
                    STATUS  mandatory
                    DESCRIPTION
                    "Table of switch module LEDs information."
                    ::= { smLEDs 1 }

       smLEDsEntry OBJECT-TYPE
                     SYNTAX SMLEDsEntry
                     ACCESS  not-accessible
                     STATUS  mandatory
                     DESCRIPTION
                     "Switch module LEDs information entry"
                     INDEX { ledSMIndex }
                     ::= { smLEDsTable 1 }


       SMLEDsEntry ::= SEQUENCE {
                   ledSMIndex INTEGER,
                   ledSMLEDs  OCTET STRING  
                   }


       ledSMIndex OBJECT-TYPE
                   SYNTAX  INTEGER (0..128)
                   ACCESS  read-only
                   STATUS  mandatory
                   DESCRIPTION
                   "Switch module LEDs table index.  "
                   ::= { smLEDsEntry 1 }

       ledSMLEDs OBJECT-TYPE
                   SYNTAX  OCTET STRING (SIZE(256))
                   ACCESS  read-only
                   STATUS  mandatory
                   DESCRIPTION
                   "A bitmap of LEDs information on the selected switch module.  The 
                   bitmap is a string containing a list of 1's and 0's.  Every 4 bytes
                   are used to represent a led state. The first 64 bytes represent the 
                   status of the external LEDs while the last 64 bytes represent the 
                   status of the internal port connections from the switch module to 
                   blades.  Each nible of data is presented in the bitmap format (0000) 
                   and is encoded as followed
                      - 0000: LED is not present
                      - 0001: LED is off
                      - 0010: LED is on 
                      
                   Note: The data is read from left to right, starting out with blade 
                   server 1 and so on."   
                   ::= { smLEDsEntry 2 }

     -- ************************************************************************
     -- BladeCenter T System Health
     -- ************************************************************************
     -- 2.9
     telcoSystemHealth OBJECT IDENTIFIER ::= { monitors 9 }

     -- ************************************************************************
     -- BladeCenter T System Health Status
     -- ************************************************************************
     -- 2.9.1
     telcoSystemHealthStat  OBJECT-TYPE
                   SYNTAX  INTEGER {
                                     critical-power(6),
                                     critical(5),
                                     major-power(4),
                                     major(3),
                                     minor-power(2),
                                     minor(1),
                                     normal(255)
                                   }
                   ACCESS  read-only
                   STATUS  mandatory
                   DESCRIPTION
                   "Indicates status of system health for the system in which the 
                   MM resides. Value of 'critical' indicates a non-recoverable 
                   service affecting condition has occurred that requires an 
                   immediate action. A value of 'major' indicates a critical 
                   service affecting condition has occurred that requires an urgent
                   action. A value of 'minor' indicates a non-service affecting 
                   condition has occurred. Corrective action should be taken in 
                   order to prevent a more serious fault. A value of 'normal' 
                   indicates that the system is operating normally. Severity level
                   with '-power' indicates the failure relates to the power resource.
                   
                   NOTE: This MIB is for BladeCenter T only." 
                   ::= { telcoSystemHealth 1 }

     -- ************************************************************************
     -- BladeCenter T System Health Summary
     -- ************************************************************************
     -- 2.9.2
     telcoSystemHealthSummaryTable OBJECT-TYPE
                   SYNTAX  SEQUENCE OF TelcoSystemHealthSummaryEntry
                   ACCESS  not-accessible
                   STATUS  mandatory
                   DESCRIPTION
                   "Table of System Health summary. Contains more detailed
                   information about the reasons for the overall system
                   health status.
                   
                   NOTE: This MIB is for BladeCenter T only." 
                   ::= { telcoSystemHealth 2 }

     telcoSystemHealthSummaryEntry OBJECT-TYPE
                   SYNTAX TelcoSystemHealthSummaryEntry
                   ACCESS  not-accessible
                   STATUS  mandatory
                   DESCRIPTION
                   "BladeCenter T System Health Summary entry.
                   
                   NOTE: This MIB is for BladeCenter T only." 
                   INDEX { telcoSystemHealthSummaryIndex }
                   ::= { telcoSystemHealthSummaryTable 1 }


     TelcoSystemHealthSummaryEntry ::= SEQUENCE {
                   telcoSystemHealthSummaryIndex INTEGER,
                   telcoSystemHealthSummarySeverity OCTET STRING,
                   telcoSystemHealthSummaryDescription OCTET STRING,
                   telcoSystemHealthSummaryEventName INTEGER,
                   telcoSystemHealthSummaryEventKeyID OCTET STRING,
                   telcoSystemHealthSummaryAcknowledge INTEGER
     }


     telcoSystemHealthSummaryIndex  OBJECT-TYPE
                   SYNTAX  INTEGER
                   ACCESS  read-only
                   STATUS  mandatory
                   DESCRIPTION
                   "BladeCenter T System Health Summary Index.
                   
                   NOTE: This MIB is for BladeCenter T only." 
                   ::= { telcoSystemHealthSummaryEntry 1 }

     telcoSystemHealthSummarySeverity  OBJECT-TYPE
                   SYNTAX  OCTET STRING
                   ACCESS  read-only
                   STATUS  mandatory
                   DESCRIPTION
                   "BladeCenter T System Health Summary Severity. The values 
                   and meanings are as follows:
                      0x06 Critical-Power
                      0x05 Critical 
                      0x04 Major-Power
                      0x03 Major 
                      0x02 Minor-Power
                      0x01 Minor 
                      0xFF Normal
                      
                   NOTE: This MIB is for BladeCenter T only." 
                   ::= { telcoSystemHealthSummaryEntry 2 }

     telcoSystemHealthSummaryDescription  OBJECT-TYPE
                   SYNTAX  OCTET STRING
                   ACCESS  read-only
                   STATUS  mandatory
                   DESCRIPTION
                   "BladeCenter T System Health Summary Description.
                   
                   NOTE: This MIB is for BladeCenter T only." 
                   ::= { telcoSystemHealthSummaryEntry 3 }
                 
     telcoSystemHealthSummaryEventName  OBJECT-TYPE
                   SYNTAX INTEGER 
                   ACCESS  read-only
                   STATUS  mandatory
                   DESCRIPTION
                   "BladeCenter T System Health Summary Event Name.
                   
                   NOTE: This MIB is for BladeCenter T only." 
                   ::= { telcoSystemHealthSummaryEntry 4 }
       
     telcoSystemHealthSummaryEventKeyID  OBJECT-TYPE
                   SYNTAX OCTET STRING 
                   ACCESS  read-only
                   STATUS  mandatory
                   DESCRIPTION
                   "BladeCenter T System Health Summary Event Key ID. An octet string 
                   expressed as 'mmm:aaa:ggg:iii' where: 
                      m : Module ID value of decimal digits(1-255) or 
                          blank space(s) for leading zero(s)
                      a : Alarm ID value of decimal digits(1-255) or
                          blank space(s) for leading zero(s) 
                      g : Gen ID value of decimal digits(1-255) or 
                          blank space(s) for leading zero(s)
                      i : GenInfo ID value of decimal digits(1-255) or
                          blank space(s) for leading zero(s)
                           
                   NOTE: This MIB is for BladeCenter T only." 
                   ::= { telcoSystemHealthSummaryEntry 5 }
     
     telcoSystemHealthSummaryAcknowledge  OBJECT-TYPE
                   SYNTAX INTEGER {
                     unacknowledged(0),
                     acknowledged(1)
                   }
                   ACCESS  read-only
                   STATUS  mandatory
                   DESCRIPTION
                   "BladeCenter T System Health Summary Acknowledge. Indicates whether the
                   alarm event is acknowledged or unacknowledged.
                   
                   NOTE: This MIB is for BladeCenter T only." 
                   ::= { telcoSystemHealthSummaryEntry 6 }
    
      


    -- ********************************************************************************
    -- Fuel Gauge / Power Management 
    -- ********************************************************************************
    -- 2.10
    fuelGauge OBJECT IDENTIFIER ::= { monitors 10 }

     -- ********************************************************************************
     -- Fuel Gauge
     -- ********************************************************************************
     fuelGaugeInformation  OBJECT IDENTIFIER ::= { fuelGauge 1 }
     
      fuelGaugeTable OBJECT-TYPE
                   SYNTAX  SEQUENCE OF FuelGaugeEntry
                   ACCESS  not-accessible
                   STATUS  mandatory
                   DESCRIPTION
                   "Table of Fuel Gauge information."
                   ::= { fuelGaugeInformation 1 }

      fuelGaugeEntry OBJECT-TYPE
                   SYNTAX FuelGaugeEntry
                   ACCESS  not-accessible
                   STATUS  mandatory
                   DESCRIPTION
                   "Fuel Gauge entry"
                   INDEX { fuelGaugeIndex }
                   ::= { fuelGaugeTable 1 }

      FuelGaugeEntry ::= SEQUENCE {
                 fuelGaugeIndex INTEGER,
                 fuelGaugePowerDomainNumber INTEGER,
                 fuelGaugeStatus OCTET STRING,
                 fuelGaugeFirstPowerModule OCTET STRING,
                 fuelGaugeSecondPowerModule OCTET STRING,
                 fuelGaugePowerManagementPolicySetting INTEGER,
                 fuelGaugeTotalPower OCTET STRING,
                 fuelGaugeAllocatedPower OCTET STRING,
                 fuelGaugeRemainingPower OCTET STRING,
                 fuelGaugePowerInUsed OCTET STRING
      }

      fuelGaugeIndex  OBJECT-TYPE
                 SYNTAX  INTEGER
                 ACCESS  read-only
                 STATUS  mandatory
                 DESCRIPTION
                 "Fuel Gauge Table Index."
                 ::= { fuelGaugeEntry 1 }

      fuelGaugePowerDomainNumber  OBJECT-TYPE
                 SYNTAX  INTEGER {
                   powerDomain1(1), 
                   powerDomain2(2)       
                 }
                 ACCESS  read-only
                 STATUS  mandatory
                 DESCRIPTION
                 "Fuel Gauge Table Power Domain Number."
                 ::= { fuelGaugeEntry 2 }
                 
      fuelGaugeStatus  OBJECT-TYPE
                 SYNTAX  OCTET STRING
                 ACCESS  read-only
                 STATUS  mandatory
                 DESCRIPTION
                 "Fuel Gauge Table Status for the power domain.  
                 The response will start out with a numeric value (0 = unknown, 
                 1 = good, 2 = waring, and 3: bad), followed by a text message."
                 ::= { fuelGaugeEntry 3 }

      fuelGaugeFirstPowerModule  OBJECT-TYPE
                 SYNTAX  OCTET STRING
                 ACCESS  read-only
                 STATUS  mandatory
                 DESCRIPTION
                 "Fuel Gauge Table First Power Module capacity in Watts in the power domain.  
                 
                 Note: First power module in power domain 1 and 2 is in bay 1 
                 and 3 respectively."
                 ::= { fuelGaugeEntry 4 }

      fuelGaugeSecondPowerModule  OBJECT-TYPE
                 SYNTAX  OCTET STRING
                 ACCESS  read-only
                 STATUS  mandatory
                 DESCRIPTION
                 "Fuel Gauge Table Second Power Module capacity in Watts in the power domain.
                 
                 Note: Second power module in power domain 1 and 2 is in bay 2 
                 and 4 respectively."
                 ::= { fuelGaugeEntry 5 }

      fuelGaugePowerManagementPolicySetting  OBJECT-TYPE
                 SYNTAX  INTEGER {
                   redundantWithoutPerformanceImpact(0),
                   redundantWithPerformanceImpact(1), 
                   nonRedundant(2),
                   notApplicable(255)
                 }
                 ACCESS  read-only
                 STATUS  mandatory
                 DESCRIPTION
                 "Fuel Gauge Table for the Power Management Policy Setting for each power domain.
                 When a 1200W or 1400W power module is installed in the domain 
                 the power management policy will not be applicable. 
                 In addition the power consumption in this domain will not be monitored."
                 ::= { fuelGaugeEntry 6 }
       
       fuelGaugeTotalPower  OBJECT-TYPE
                 SYNTAX  OCTET STRING
                 ACCESS  read-only
                 STATUS  mandatory
                 DESCRIPTION
                 "This field displays the total available power for each power domain based on 
                 installed power modules and the current Power Management Policy Setting.                 
                 When a 1200W or 1400W power module is installed in the domain 
                 the power management policy will not be applicable. 
                 In addition the power consumption in this domain will not be monitored."
                 ::= { fuelGaugeEntry 7 }          

      fuelGaugeAllocatedPower  OBJECT-TYPE
                 SYNTAX  OCTET STRING
                 ACCESS  read-only
                 STATUS  mandatory
                 DESCRIPTION
                 "This field displays the power that has been reserved in each power domain.                   
                 Note: 1) Power is always reserved in domain 1 for two management modules and 
                 two I/O modules.  2) Power is reserved for I/O modules installed in bay 3 and 
                 4  (Powered on or standby). 3) Power is reserved for each installed Blade. 
                 Blades in a standby state (not powered on) will reserve a certain amount power.
                 When a 1200W or 1400W power module is installed in the domain 
                 the power management policy will not be applicable. 
                 In addition the power consumption in this domain will not be monitored."
                 ::= { fuelGaugeEntry 8 }          

      fuelGaugeRemainingPower  OBJECT-TYPE
                 SYNTAX  OCTET STRING
                 ACCESS  read-only
                 STATUS  mandatory
                 DESCRIPTION
                 "This field displays the remaining power available in each domain. 
                 Remaining Power = Total Power minus Power In Use 
                 When a 1200W or 1400W power module is installed in the domain 
                 the power management policy will not be applicable. 
                 In addition the power consumption in this domain will not be monitored."
                 ::= { fuelGaugeEntry 9 }
     
      fuelGaugePowerInUsed  OBJECT-TYPE
                 SYNTAX  OCTET STRING
                 ACCESS  read-only
                 STATUS  mandatory
                 DESCRIPTION
                 "This field displays the total power being used in each power domain.
                 When a 1200W or 1400W power module is installed in the domain 
                 the power management policy will not be applicable. 
                 In addition the power consumption in this domain will not be monitored."
                 ::= { fuelGaugeEntry 10 }          

     -- ********************************************************************************
     -- Fuel Gauge Power Domain 1
     -- ********************************************************************************
     powerDomain1  OBJECT IDENTIFIER ::= { fuelGauge 2 }
             
      powerDomain1Table OBJECT-TYPE
                   SYNTAX  SEQUENCE OF PowerDomain1Entry
                   ACCESS  not-accessible
                   STATUS  mandatory
                   DESCRIPTION
                   "Table of Power Domain 1."
                   ::= { powerDomain1 1}

      powerDomain1Entry OBJECT-TYPE
                   SYNTAX PowerDomain1Entry
                   ACCESS  not-accessible
                   STATUS  mandatory
                   DESCRIPTION
                   "Fuel Gauge entry"
                   INDEX { pd1Index }
                   ::= { powerDomain1Table 1 }


      PowerDomain1Entry ::= SEQUENCE {
                 pd1Index INTEGER,
                 pd1BayNumber OCTET STRING,
                 pd1BladePrimarySlot INTEGER, 
                 pd1ModuleStatus INTEGER,
                 pd1ModuleName OCTET STRING,
                 pd1ModuleState INTEGER,
                 pd1ModuleAllocatedPowerCurrent OCTET STRING,
                 pd1ModuleAllocatedPowerMax OCTET STRING,
                 pd1ModuleAllocatedPowerMin OCTET STRING,
                 pd1ModuleCPUDutyCycles OCTET STRING,
                 pd1ModuleThrottle INTEGER
      }
 
      pd1Index  OBJECT-TYPE
                 SYNTAX  INTEGER
                 ACCESS  read-only
                 STATUS  mandatory
                 DESCRIPTION
                 "Power Domain 1 Table Index."
                 ::= { powerDomain1Entry 1 }

      pd1BayNumber  OBJECT-TYPE
                 SYNTAX  OCTET STRING
                 ACCESS  read-only
                 STATUS  mandatory
                 DESCRIPTION
                 "Power Domain 1 Table Bay Number.
                  The following Bay Number IDs are used in the BladeCenter:
                   notApplicable(1), 
                   notApplicable(2), 
                   blowerBay1(3), 
                   blowerBay2(4), 
                   managementModuleBay1(5), 
                   managementModuleBay2(6),
                   switchModuelBay1(7), 
                   switchModuleBay2(8),
                   switchModuleBay3(9),
                   switchModuleBay4(10),
                   serverBladeBay1(11),  
                   serverBladeBay2(12),  
                   serverBladeBay3(13),  
                   serverBladeBay4(14),  
                   serverBladeBay5(15),  
                   serverBladeBay6(16),
                   notApplicable(17)
                  The following Bay Number IDs are used in the BladeCenter T:
                   notApplicable(1), 
                   notApplicable(2), 
                   blowerBay1(3), 
                   blowerBay2(4), 
                   blowerBay3(5) (if Power Domain 2 is not available),
                   blowerBay4(6) (if Power Domain 2 is not available),
                   managementModuleBay1(7), 
                   managementModuleBay2(8),
                   switchModuelBay1(9), 
                   switchModuleBay2(10),
                   switchModuleBay3(11),
                   switchModuleBay4(12),
                   serverBladeBay1(13),  
                   serverBladeBay2(14),  
                   serverBladeBay3(15),  
                   serverBladeBay4(16),  
                   notApplicable(17)"
                 ::= { powerDomain1Entry 2 }

      pd1BladePrimarySlot  OBJECT-TYPE
                 SYNTAX  INTEGER  {
                   no(0), 
                   yes(1),
                   notApplicable(255)
                 }       
                 ACCESS  read-only
                 STATUS  mandatory
                 DESCRIPTION
                 "Power Domain 1 Table Blade Primary Slot can be useful 
                 when a server blade spans multiple slots (e.g. double wide or 
                 triple wide).  For example if the blade is double wide and 
                 is installed in slot 3 and 4.  3 is primary slot while 4 is not." 
                 ::= { powerDomain1Entry 3 }

      pd1ModuleStatus  OBJECT-TYPE
                 SYNTAX  INTEGER  {
                   insufficientPower(0), 
                   moduleIsThrottling(1),
                   moduleNotThrottling(2),
                   notApplicable(255)
                 }       
                 ACCESS  read-only
                 STATUS  mandatory
                 DESCRIPTION
                 "Power Domain 1 Table Module Throttle Status."
                 ::= { powerDomain1Entry 4 }

      pd1ModuleName  OBJECT-TYPE
                 SYNTAX  OCTET STRING
                 ACCESS  read-only
                 STATUS  mandatory
                 DESCRIPTION
                 "Power Domain 1 Table Module Name."
                 ::= { powerDomain1Entry 5 }

      pd1ModuleState  OBJECT-TYPE
                 SYNTAX  INTEGER {
                   standby(0),
                   on(1),
                   notPresent(2),
                   notApplicable(255)
                 }       
                 ACCESS  read-only
                 STATUS  mandatory
                 DESCRIPTION
                 "Power Domain 1 Table Module State."
                 ::= { powerDomain1Entry 6 }
                                                         
      pd1ModuleAllocatedPowerCurrent  OBJECT-TYPE
                 SYNTAX  OCTET STRING
                 ACCESS  read-only
                 STATUS  mandatory
                 DESCRIPTION
                 "Power Domain 1 Table Allocated Power Current indicates the current power  
                 allocation for the module in Watts. When a 1200W or 1400W power module is 
                 installed in the domain the power management policy will not be applicable. 
                 In addition the power consumption in this domain will not be monitored.
                 
                 Note: When a server blade spans multiple slots (e.g. double wide or 
                 triple wide), the current power allocation for the module is equally 
                 divided among the slots."
                 ::= { powerDomain1Entry 7 }

      pd1ModuleAllocatedPowerMax  OBJECT-TYPE
                 SYNTAX  OCTET STRING
                 ACCESS  read-only
                 STATUS  mandatory
                 DESCRIPTION
                 "Power Domain 1 Table Allocated Power Max indicates the maximum power 
                 allocation for the module in Watts.  It is indicative of the maximum 
                 amout of power the module will consume in the domain when it is 
                 fully popolated with memory chips, expansion cards, etc. 
                 When a 1200W or 1400W power module is installed in the domain 
                 the power management policy will not be applicable. 
                 In addition the power consumption in this domain will not be monitored.
                 
                 Note: When a server blade spans multiple slots (e.g. double wide or 
                 triple wide), the maximum power allocation for the module is equally 
                 divided among the slots."
                 ::= { powerDomain1Entry 8 }

      pd1ModuleAllocatedPowerMin  OBJECT-TYPE
                 SYNTAX  OCTET STRING
                 ACCESS  read-only
                 STATUS  mandatory
                 DESCRIPTION
                 "Power Domain 1 Table Allocated Power Min indicates the minumum power 
                 allocation for the module in Watts.  It is indicative of the minumum 
                 power consumption of the component in the domain based on its 
                 maximum throttle limit. When a 1200W or 1400W power module is installed 
                 in the domain the power management policy will not be applicable. 
                 In addition the power consumption in this domain will not be monitored.
                 
                 Note: When a server blade spans multiple slots (e.g. double wide or 
                 triple wide), the minimum power allocation for the module is equally 
                 divided among the slots."
                 ::= { powerDomain1Entry 9 }
      
      pd1ModuleCPUDutyCycles  OBJECT-TYPE
                 SYNTAX  OCTET STRING
                 ACCESS  read-only
                 STATUS  mandatory
                 DESCRIPTION
                 "Power Domain 1 Table Module CPUs Duty Cycles applies to blade 
                 servers only.  It displays the duty cycle for each CPU on the blade 
                 as a percentage.  Note that some blades do not report the CPU 
                 duty cycles.  In this case, 'notApplicable' will be displayed.
                 When a 1200W or 1400W power module is installed in the domain 
                 the power management policy will not be applicable. 
                 In addition the power consumption in this domain will not be monitored.
           
                 Note: The CPU duty cycles are reported only on a primary slot when 
                 a server blade spans multiple slots (e.g. double wide or 
                 triple wide).  For example if the blade is double wide and 
                 is installed in slot 3 and 4.  3 is primary slot while 4 is not.
                 The CPU duty cycles are reported on slot 3 while 'notApplicable' 
                 is displayed for slot 4." 
                 ::= { powerDomain1Entry 10 }

      pd1ModuleThrottle  OBJECT-TYPE
                 SYNTAX  INTEGER  {
                   no(0), 
                   yes(1),
                   notApplicable(255)
                 }       
                 ACCESS  read-only
                 STATUS  mandatory
                 DESCRIPTION
                 "Power Domain 1 Table Module Throttle indicates whether the 
                 server blade may be allowed to throttle or not.
                 When a 1200W or 1400W power module is installed in the domain 
                 the power management policy will not be applicable. 
                 In addition the power consumption in this domain will not be monitored." 
                 ::= { powerDomain1Entry 11 }
                 
     -- ********************************************************************************
     -- Fuel Gauge Power Domain 2
     -- ********************************************************************************
     powerDomain2  OBJECT IDENTIFIER ::= { fuelGauge 3 }

      powerDomain2Table OBJECT-TYPE
                   SYNTAX  SEQUENCE OF PowerDomain2Entry
                   ACCESS  not-accessible
                   STATUS  mandatory
                   DESCRIPTION
                   "Table of Power Domain 2."
                   ::= { powerDomain2 1 }

      powerDomain2Entry OBJECT-TYPE
                   SYNTAX PowerDomain2Entry
                   ACCESS  not-accessible
                   STATUS  mandatory
                   DESCRIPTION
                   "Fuel Gauge entry"
                   INDEX { pd2Index }
                   ::= { powerDomain2Table 1 } 

      PowerDomain2Entry ::= SEQUENCE {
                 pd2Index INTEGER,
                 pd2BayNumber OCTET STRING,
                 pd2BladePrimarySlot INTEGER,
                 pd2ModuleStatus INTEGER,
                 pd2ModuleName OCTET STRING,
                 pd2ModuleState INTEGER,
                 pd2ModuleAllocatedPowerCurrent OCTET STRING,
                 pd2ModuleAllocatedPowerMax OCTET STRING,
                 pd2ModuleAllocatedPowerMin OCTET STRING,
                 pd2ModuleCPUDutyCycles OCTET STRING,
                 pd2ModuleThrottle INTEGER
      }

      pd2Index  OBJECT-TYPE
                 SYNTAX  INTEGER
                 ACCESS  read-only
                 STATUS  mandatory
                 DESCRIPTION
                 "Power Domain 2 Table Index."
                 ::= { powerDomain2Entry 1 }

      pd2BayNumber  OBJECT-TYPE
                 SYNTAX  OCTET STRING 
                 ACCESS  read-only
                 STATUS  mandatory
                 DESCRIPTION
                 "Power Domain 2 Table Bay Number.
                  The following Bay Number IDs are used in the BladeCenter:
                   serverBladeBay7(1),  
                   serverBladeBay8(2),  
                   serverBladeBay9(3),  
                   serverBladeBay10(4), 
                   serverBladeBay11(5), 
                   serverBladeBay12(6),
                   serverBladeBay13(7), 
                   serverBladeBay14(8),
                   notApplicable(9)
                  The following Bay Number IDs are used in the BladeCenter T:
                   blowerBay3(1), 
                   blowerBay4(2), 
                   serverBladeBay5(3),  
                   serverBladeBay6(4),  
                   serverBladeBay7(5),  
                   serverBladeBay8(6),  
                   notApplicable(7),  
                   notApplicable(8),  
                   notApplicable(9)"  
                 ::= { powerDomain2Entry 2 }

      pd2BladePrimarySlot  OBJECT-TYPE
                 SYNTAX  INTEGER  {
                   no(0), 
                   yes(1),
                   notApplicable(255)
                 }       
                 ACCESS  read-only
                 STATUS  mandatory
                 DESCRIPTION
                 "Power Domain 2 Table Blade Primary Slot can be useful 
                 when a server blade spans multiple slots (e.g. double wide or 
                 triple wide).  For example if the blade is double wide and 
                 is installed in slot 3 and 4.  3 is primary slot while 4 is not." 
                 ::= { powerDomain2Entry 3 }

      pd2ModuleStatus  OBJECT-TYPE
                 SYNTAX  INTEGER {
                   insufficientPower(0), 
                   moduleIsThrottling(1),
                   moduleNotThrottling(2),
                   notApplicable(255)
                 }
                 ACCESS  read-only
                 STATUS  mandatory
                 DESCRIPTION
                 "Power Domain 2 Table Module throttle status."
                 ::= { powerDomain2Entry 4 }

      pd2ModuleName  OBJECT-TYPE
                 SYNTAX  OCTET STRING
                 ACCESS  read-only
                 STATUS  mandatory
                 DESCRIPTION
                 "Power Domain 2 Table Module Name."
                 ::= { powerDomain2Entry 5 }

      pd2ModuleState  OBJECT-TYPE
                 SYNTAX  INTEGER {
                   standby(0),
                   on(1),
                   notPresent(2),
                   notApplicable(255)
                 }
                 ACCESS  read-only
                 STATUS  mandatory
                 DESCRIPTION
                 "Power Domain 2 Table Power State."
                 ::= { powerDomain2Entry 6 }
     
      pd2ModuleAllocatedPowerCurrent  OBJECT-TYPE
                 SYNTAX  OCTET STRING
                 ACCESS  read-only
                 STATUS  mandatory
                 DESCRIPTION
                 "Power Domain 2 Table Allocated Power Current indicates the current power 
                 allocation for the module. When a 1200W or 1400W power module is 
                 installed in the domain the power management policy will not be applicable. 
                 In addition the power consumption in this domain will not be monitored.
                 
                 Note: When a server blade spans multiple slots (e.g. double wide or 
                 triple wide), the current power allocation for the module is equally 
                 divided among the slots."
                 ::= { powerDomain2Entry 7 }

      pd2ModuleAllocatedPowerMax  OBJECT-TYPE
                 SYNTAX  OCTET STRING
                 ACCESS  read-only
                 STATUS  mandatory
                 DESCRIPTION
                 "Power Domain 2 Table Allocated Power Max indicates the maximum power 
                 allocation for the module in Watts.  It is indicative of the maximum 
                 amount of power the module will consume in the domain when it is 
                 fully popolated with memory chips, expansion cards, etc.
                 When a 1200W or 1400W power module is installed in the domain 
                 the power management policy will not be applicable. In addition 
                 the power consumption in this domain will not be monitored.
                 
                 Note: When a server blade spans multiple slots (e.g. double wide or 
                 triple wide), the maximum power allocation for the module is equally 
                 divided among the slots."
                 ::= { powerDomain2Entry 8 }

      pd2ModuleAllocatedPowerMin  OBJECT-TYPE
                 SYNTAX  OCTET STRING
                 ACCESS  read-only
                 STATUS  mandatory
                 DESCRIPTION
                 "Power Domain 2 Table Allocated Power Min indicates the minumum power 
                 allocation for the module in Watts.  It is indicative of the minumum 
                 power consumption of the component in the domain based on its 
                 maximum throttle limit. When a 1200W or 1400W power module is 
                 installed in the domain the power management policy will not be applicable. 
                 In addition the power consumption in this domain will not be monitored.

                 Note: When a server blade spans multiple slots (e.g. double wide or 
                 triple wide), the minimum power allocation for the module is equally 
                 divided among the slots."
                 ::= { powerDomain2Entry 9 }

      pd2ModuleCPUDutyCycles  OBJECT-TYPE
                 SYNTAX  OCTET STRING
                 ACCESS  read-only
                 STATUS  mandatory
                 DESCRIPTION
                 "Power Domain 2 Table Module CPUs Duty Cycles applies to blade 
                 servers only.  It displays the duty cycle for each CPU on the blade 
                 as a percentage.  Note that some blades do not report the CPU 
                 duty cycles.  In this case, 'notApplicable' will be displayed.
                 When a 1200W or 1400W power module is installed in the domain 
                 the power management policy will not be applicable. 
                 In addition the power consumption in this domain will not be monitored.
                 
                 Note: The CPU duty cycles are reported only on a primary slot when 
                 a server blade spans multiple slots (e.g. double wide or 
                 triple wide).  For example if the blade is double wide and 
                 is installed in slot 3 and 4.  3 is primary slot while 4 is not.  
                 The CPU duty cycles are reported on slot 3 while 'notApplicable' 
                 is displayed for slot 4. " 
                 ::= { powerDomain2Entry 10 }

      pd2ModuleThrottle  OBJECT-TYPE
                 SYNTAX  INTEGER  {
                   no(0), 
                   yes(1),
                   notApplicable(255)
                 }       
                 ACCESS  read-only
                 STATUS  mandatory
                 DESCRIPTION
                 "Power Domain 2 Table Module Throttle indicates whether the 
                 server blade may be allowed to throttle or not. 
                 When a 1200W or 1400W power module is installed in the domain 
                 the power management policy will not be applicable. 
                 In addition the power consumption in this domain will not be monitored." 
                 ::= { powerDomain2Entry 11 }
                 
    
    -- ********************************************************************************
    -- Error logs
    -- ********************************************************************************
    -- 3.4
    eventLog   OBJECT IDENTIFIER ::= { errorLogs 4 }

     -- 3.4.6
     readEventLogTable  OBJECT-TYPE
                    SYNTAX  SEQUENCE OF ReadEventLogEntry
                    ACCESS  not-accessible
                    STATUS  mandatory
                    DESCRIPTION
                    "Table of event log entry information."
                    ::= { eventLog 2 }

      readEventLogEntry OBJECT-TYPE
                    SYNTAX ReadEventLogEntry
                    ACCESS  not-accessible
                    STATUS  mandatory
                    DESCRIPTION
                    "Event log entry table entry"
                    INDEX { readEventLogIndex }
                    ::= { readEventLogTable 1 }


      ReadEventLogEntry ::= SEQUENCE {
                  readEventLogIndex INTEGER,
                  readEventLogString OCTET STRING
      }


      readEventLogIndex  OBJECT-TYPE
                  SYNTAX  INTEGER
                  ACCESS  read-only
                  STATUS  mandatory
                  DESCRIPTION
                  "The event log index number.  For consistent results,
                  view as a table and not as individual entries."
                  ::= { readEventLogEntry 1 }

      readEventLogString OBJECT-TYPE
                  SYNTAX  OCTET STRING
                  ACCESS  read-only
                  STATUS  mandatory
                  DESCRIPTION
                  "A string of data detailing an event.  For consistent
                  results, view as a table and not as individual entries."
                  ::= { readEventLogEntry 2 }


     -- 3.4.3
     clearEventLog OBJECT-TYPE
                  SYNTAX  INTEGER {
                    execute(1)
                  }
                  ACCESS  read-write
                  STATUS  mandatory
                  DESCRIPTION
                  "Clear the event log. 
                  
                  NOTE: Value returned for the GET command is meaningless for this 
                  MIB."
                  ::= { eventLog 3 }

     -- 3.4.4
     monitorLogStateEvents OBJECT-TYPE
                  SYNTAX  INTEGER {
                    disabled(0),
                    enabled(1)
                  }
                  ACCESS  read-write
                  STATUS  mandatory
                  DESCRIPTION
                  "If disabled, it means the info LED will not turn on when the log gets full 
                  and no alerts will be sent out. If enabled, the LED will turn on when the log 
                  gets full and alerts will be sent out."
                  ::= { eventLog 4 }

    -- ********************************************************************************
    -- Event Log Information
    -- ********************************************************************************
    -- 3.4, 3.5   this looks like 3.1 and 3.4.1, but might be all that's needed.
--  eventLog   OBJECT IDENTIFIER ::= { errorLogs 4 }
--
--   eventLogTable OBJECT-TYPE
--                  SYNTAX  SEQUENCE OF EventLogEntry
--                  ACCESS  not-accessible
--                  STATUS  mandatory
--                  DESCRIPTION
--                  "Table of event logs."
--                  ::= { eventLog 2 }
--
--   eventLogEntry OBJECT-TYPE
--                  SYNTAX EventLogEntry
--                  ACCESS  not-accessible
--                  STATUS  mandatory
--                  DESCRIPTION
--                  "Event log entries."
--                  INDEX { eventLogIndex }
--                  ::= { eventLogTable 1 }
--
--
--   EventLogEntry ::= SEQUENCE {
--                eventLogIndex INTEGER,
--                eventLogString DisplayString
--   }
--
--
--   eventLogIndex   OBJECT-TYPE
--                SYNTAX  INTEGER
--                ACCESS  read-only
--                STATUS  mandatory
--                DESCRIPTION
--                "Event log index number."
--                ::= { eventLogEntry 1 }
--
--   eventLogString OBJECT-TYPE
--                SYNTAX  OCTET STRING (SIZE(0..8))
--                ACCESS  read-only
--                STATUS  mandatory
--                DESCRIPTION
--                "Contains a string of information to detail the event."
--                ::= { eventLogEntry 2}
--
--
--    3.4.3, 3.5.3
--   eventLogClr    OBJECT-TYPE
--                SYNTAX  INTEGER {
--                  execute(1)
--                 }
--                ACCESS  read-write
--                STATUS  mandatory
--                DESCRIPTION
--                "Clear the event log.
--
--                NOTE: Value returned by the GET command is meaningless for this
--                MIB object."
--                ::= { eventLog 3 }

--  ********************************************************************************
--  Configure the MM
--  ********************************************************************************
    -- ********************************************************************************
    -- Remote Access Configuration
    -- ********************************************************************************
    -- 4.1
    remoteAccessConfig  OBJECT IDENTIFIER ::= { configureSP 1 }

     -- ********************************************************************************
     -- General Remote Access and Remote Alerts Configuration
     -- ********************************************************************************
     generalRemoteCfg    OBJECT IDENTIFIER ::= { remoteAccessConfig 1 }

      remoteAlertRetryDelay OBJECT-TYPE
                   SYNTAX  INTEGER {
                     noDelay(0),
                     oneHalfMinute(30),
                     oneMinute(60),
                     oneAndHalfMinutes(90),
                     twoMinutes(120),
                     twoAndHalfMinutes(150),
                     threeMinutes(180),
                     threeAndHalfMinutes(210),
                     fourMinutes(240)
                   }
                   ACCESS  read-write
                   STATUS  mandatory
                   DESCRIPTION
                   "Number in seconds to delay between retries if sending a
                   remote alert is unsuccessful."
                   ::= { generalRemoteCfg 3 }
                   
      remoteAlertRetryCount OBJECT-TYPE
                   SYNTAX  INTEGER {
                     noretry(0),
                     retry1(1),
                     retry2(2),
                     retry3(3),
                     retry4(4),
                     retry5(5),
                     retry6(6),
                     retry7(7),
                     retry8(8)
                   }
                   ACCESS  read-write
                   STATUS  mandatory
                   DESCRIPTION
                   "Number of additional times a remote alert will be
                   retried if not succesfully sent. A value of zero indicates
                   no retries will be attempted."
                   ::= { generalRemoteCfg 4 }

      remoteAlertEntryDelay OBJECT-TYPE
                   SYNTAX  INTEGER {
                     noDelay(0),
                     oneHalfMinute(30),
                     oneMinute(60),
                     oneAndHalfMinutes(90),
                     twoMinutes(120),
                     twoAndHalfMinutes(150),
                     threeMinutes(180),
                     threeAndHalfMinutes(210),
                     fourMinutes(240)
                   }
                   ACCESS  read-write
                   STATUS  mandatory
                   DESCRIPTION
                   "Number in seconds to delay between entries if sending a
                   remote alert is unsuccessful."
                   ::= { generalRemoteCfg 5 }

      remoteAccessTamperDelay OBJECT-TYPE
                   SYNTAX  INTEGER {
                     nowait(0),
                     oneMinute(1),
                     twoMinutes(2),
                     threeMinutes(3),
                     fourMinutes(4),
                     fiveMinutes(5),
                     sixMinutes(6),
                     sevenMinutes(7),
                     tenMinutes(10),
                     fifteenMinutes(15),
                     twentyMinutes(20),
                     thirtyMinutes(30),
                     sixtyMinutes(60),
                     oneTwentyMinutes(120),
                     oneEightyMinutes(180),
                     twoFortyMinutes(240)
                   }
                   ACCESS  read-write
                   STATUS  mandatory
                   DESCRIPTION
                   "Number in minutes to prohibit a remote login attempt
                   after more than 5 sequential login attempts have failed."
                   ::= { generalRemoteCfg 6 }


      userAuthenticationMethod OBJECT-TYPE
                    SYNTAX  INTEGER {
                       localOnly(0),
                       ldapOnly(1),
                       localFirstThenLdap(2),
                       ldapFirstThenLocal(3)
                    }
                    ACCESS  read-write
                    STATUS  mandatory
                    DESCRIPTION
                    "Use this field to specify how users attempting to login should be authenticated. 
                    There are two methods: 
                       Local authentication. Userid and password are verified by searching the list 
                          of users locally configured under Local Login Profiles.
                       LDAP based authentication. Users are authenticated via a remote LDAP server.
                    One or both authentication methods can be selected. If both methods should be 
                    used, the order must be specified."
                   ::= { generalRemoteCfg 7 }

--      allowModemLogin OBJECT-TYPE
--                    SYNTAX  INTEGER {
--                       disabled(0),
--                       enabled(1)
--                    }
--                    ACCESS  read-write
--                    STATUS  mandatory
--                    DESCRIPTION
--                    "Allow the user login through modem connection"
--                   ::= { generalRemoteCfg 8 }

     -- ********************************************************************************
     -- Remote Alert Profiles
     -- ********************************************************************************
     -- 4.1.3
     remoteAlertIds OBJECT IDENTIFIER ::= { remoteAccessConfig 3 }

      remoteAlertIdsTable  OBJECT-TYPE
                            SYNTAX  SEQUENCE OF RemoteAlertIdsEntry
                            ACCESS  not-accessible
                            STATUS  mandatory
                            DESCRIPTION
                            "Table of remote alert entries.
                            This table lets you configure remote alert recipients.
                            You can define up to 12 unique recipients.
                            Note: All selected alert events will be sent to all
                            enabled alert recipients."
                            ::= {  remoteAlertIds 1 }

      remoteAlertIdsEntry  OBJECT-TYPE
                            SYNTAX RemoteAlertIdsEntry
                            ACCESS  not-accessible
                            STATUS  mandatory
                            DESCRIPTION
                            "Remote alert entries."
                            INDEX { remoteAlertIdEntryIndex }
                            ::= { remoteAlertIdsTable 1 }


      RemoteAlertIdsEntry ::= SEQUENCE {
                   remoteAlertIdEntryIndex INTEGER,
                   remoteAlertIdEntryStatus INTEGER,
                   remoteAlertIdEntryIpOrHostAddress OCTET STRING (SIZE(0..50)),
                   remoteAlertIdEntryTextDescription OCTET STRING (SIZE(0..32)),
                   remoteAlertIdEntryNotificationType INTEGER,
                   remoteAlertIdEmailAddr OCTET STRING (SIZE(0..64)),
                   remoteAlertIdEntrySelectiveAlert INTEGER
      }


      remoteAlertIdEntryIndex  OBJECT-TYPE
                                SYNTAX  INTEGER
                                ACCESS  read-only
                                STATUS  mandatory
                                DESCRIPTION
                                "Index for remote alert entry."
                                ::= { remoteAlertIdsEntry 1 }

      -- 4.1.3.x.1
      remoteAlertIdEntryStatus OBJECT-TYPE
                                SYNTAX  INTEGER {
                                  invalid(0),
                                  disabledAndValid(1),
                                  enabledAndValid(2)
                                }
                                ACCESS  read-write
                                STATUS  mandatory
                                DESCRIPTION
                                "Remote alert entry status, invalid means entry
                                not defined yet, disabledAndValid means entry defined
                                but not enabled to send an alert, enabledAndValid means
                                entry defined and enabled to send an alert."
                                ::= { remoteAlertIdsEntry 2 }

      -- 4.1.3.x.2
      remoteAlertIdEntryIpOrHostAddress OBJECT-TYPE
                                SYNTAX  OCTET STRING (SIZE(0..50))
                                ACCESS  read-write
                                STATUS  mandatory
                                DESCRIPTION
                                "A null terminated string that either
                                contains an IP address of the form '1.2.3.4'
                                or a host name (if DNS is enabled) for the
                                alert entry."
                                ::= { remoteAlertIdsEntry 3 }

      -- 4.1.3.x.3
      remoteAlertIdEntryTextDescription  OBJECT-TYPE
                                SYNTAX  OCTET STRING (SIZE(0..50))
                                ACCESS  read-write
                                STATUS  mandatory
                                DESCRIPTION
                                "A null terminated string that contains
                                a text description of this entry."
                                ::= { remoteAlertIdsEntry 4 }

      -- 4.1.3.x.4
      remoteAlertIdEntryNotificationType OBJECT-TYPE
                                SYNTAX  INTEGER {
                                  unknown(0),
                                  ibmDirectorOverLAN(8),
                                  snmpOverLan(4),
                                  emailOverLan(5)
                                }
                                ACCESS  read-write
                                STATUS  mandatory
                                DESCRIPTION
                                "Remote alert entry notification method.  Types include
                                unknown when the type can't be determined (read-only),
                                ibmDirectorOverLAN for a LAN alert sent over ethernet to
                                IBM director, snmpOverLan for an SNMP alert over ethernet,
                                and emailOverLan for a E-Mail alert over ethernet."
                                ::= { remoteAlertIdsEntry 5 }

      -- 4.1.3.x.8
      remoteAlertIdEmailAddr    OBJECT-TYPE
                                SYNTAX  OCTET STRING(SIZE(0..64))
                                ACCESS  read-write
                                STATUS  mandatory
                                DESCRIPTION
                                "A null terminated string that contains an
                                E-Mail Address.  For example, 'jeb@us.ibm.com'.
                                Used only for an E-mail over Lan or E-Mail over PPP
                                notification type."
                                ::= { remoteAlertIdsEntry 9 }

      -- 4.1.3.x.12
      remoteAlertIdEntrySelectiveAlert OBJECT-TYPE
                                SYNTAX  INTEGER {
                                  critOnlyAlerts(0),
                                  allAlerts(1)
                                }
                                ACCESS  read-write
                                STATUS  mandatory
                                DESCRIPTION
                                "Remote alert entry selective alert setting.  A value of
                                critOnlyAlerts will only send critical alerts to this
                                remote alert receipient, a value of allAlerts will send
                                all alerts to this remote alert recepient."
                                ::= { remoteAlertIdsEntry 13 }

      -- not in cmds doc
      generateTestAlert  OBJECT-TYPE
                   SYNTAX  INTEGER {
                    execute(1)
                   }
                   ACCESS  read-write
                   STATUS  mandatory
                   DESCRIPTION
                   "Generate a Test Alert.  This will send a test alert to all configured
                   and enabled remote alert receipients. The text portion of the alert
                   will contain 'Application Posted Alert to MM'.
                   
                   NOTE: Value returned for the GET command is meaningless for this 
                   MIB."
                   ::= { remoteAlertIds 30 }

     -- ********************************************************************************
     -- Remote Access Profiles
     -- ********************************************************************************
     -- 4.1.4
     remoteAccessIds OBJECT IDENTIFIER ::= { remoteAccessConfig 4 }

      -- 4.1.4.x
      remoteAccessIdsTable  OBJECT-TYPE
                            SYNTAX  SEQUENCE OF RemoteAccessIdsEntry
                            ACCESS  not-accessible
                            STATUS  mandatory
                            DESCRIPTION
                            "Table of remote access profiles.

                            This table lets you to configure all login profiles.
                            You can define up to 12 unique profiles.

                            Note:  By default, the remote supervisor adapter
                            comes configured with one login profile that allows remote
                            access using a login ID of 'USERID' and a password of 'PASSW0RD'
                            (the 0 is a zero).  To avoid a potential security exposure,
                            we strongly recommend that you change this default Login
                            Profile to values of your choice."
                            ::= {  remoteAccessIds 1 }

      remoteAccessIdsEntry  OBJECT-TYPE
                            SYNTAX RemoteAccessIdsEntry
                            ACCESS  not-accessible
                            STATUS  mandatory
                            DESCRIPTION
                            "Remote access entries."
                            INDEX { remoteAccessIdEntryIndex }
                            ::= { remoteAccessIdsTable 1 }


      RemoteAccessIdsEntry ::= SEQUENCE {
                   remoteAccessIdEntryIndex INTEGER(0..255),
                   remoteAccessIdEntryUserId OCTET STRING (SIZE(0..16)),
                   remoteAccessIdEntryPassword OCTET STRING (SIZE(0..16)),
--                 remoteAccessIdLastAccess OCTET STRING (SIZE(7)),
--                 remoteAccessIdEntryAccessFlags INTEGER,
--                 remoteAccessIdEntryDialBackPhoneNum OCTET STRING (SIZE(0..40)),
                   remoteAccessIdEntryEncodedLoginPw OCTET STRING (SIZE(0..36))
--                 remoteAccessIdEntryLastFloppyRemoteBoot OCTET STRING (SIZE(0..16)),
--                 remoteAccessIdEntryLastTempDirRemoteBoot OCTET STRING (SIZE(0..256))
      }


      remoteAccessIdEntryIndex  OBJECT-TYPE
                                SYNTAX  INTEGER(0..255)
                                ACCESS  read-only
                                STATUS  mandatory
                                DESCRIPTION
                                "Index for Remote access entry."
                                ::= { remoteAccessIdsEntry 1 }

      -- 4.1.4.x.1
      remoteAccessIdEntryUserId    OBJECT-TYPE
                                SYNTAX  OCTET STRING (SIZE(0..16))
                                ACCESS  read-write
                                STATUS  mandatory
                                DESCRIPTION
                                "Remote access entry null terminated string that
                                contains the user-id.  It must not be a duplicate of 
                                any previously configured ones."
                                ::= { remoteAccessIdsEntry 2 }

      -- 4.1.4.x.2
      remoteAccessIdEntryPassword OBJECT-TYPE
                                SYNTAX  OCTET STRING (SIZE(0..16))
                                ACCESS  read-write
                                STATUS  mandatory
                                DESCRIPTION
                                "Remote access password.  The password must
                                contain at least one alphabetic and one
                                non-alphabetic character and be at least 5
                                characters long, or you can leave the password
                                field blank to set an empty password.
                                
                                NOTE: Value returned by the GET command is meaningless
                                for this MIB object."
                                ::= { remoteAccessIdsEntry 3 }

-- temporarily removed
      -- 4.1.4.x.3
--    remoteAccessIdLastAccess OBJECT-TYPE
--                              SYNTAX  OCTET STRING (SIZE(7))
--                              ACCESS  read-write
--                              STATUS  mandatory
--                              DESCRIPTION
--                              "Date and time of last login.  On a write, this
--                              field has no effect."
--                              ::= { remoteAccessIdsEntry 4 }

      -- 4.1.4.x.4
--      remoteAccessIdEntryAccessFlags OBJECT-TYPE
--                                SYNTAX  INTEGER {
--                                  readWriteEnabled(0),
--                                  readOnlyEnabled(1)
--                                }
--                                ACCESS  read-write
--                                STATUS  mandatory
--                                DESCRIPTION
--                                "Remote access permission."
--                                ::= { remoteAccessIdsEntry 5 }

      -- 4.1.4.x.6
      remoteAccessIdEntryEncodedLoginPw OBJECT-TYPE
                                SYNTAX  OCTET STRING (SIZE(0..36))
                                ACCESS  read-write
                                STATUS  mandatory
                                DESCRIPTION
                                "Used only for configuration save/restore.
                                A null terminated string containing an encoded
                                concatenation of the login ID and password
                                separated by an ':'."
                                ::= { remoteAccessIdsEntry 7 }

-- temporarily removed
      -- 4.1.4.x.7
--    remoteAccessIdEntryLastFloppyRemoteBoot OBJECT-TYPE
--                              SYNTAX  OCTET STRING (SIZE(0..16))
--                              ACCESS  read-write
--                              STATUS  mandatory
--                              DESCRIPTION
--                              "The last drive used for remote booting."
--                              ::= { remoteAccessIdsEntry 8 }
--
      -- 4.1.4.x.8
--    remoteAccessIdEntryLastTempDirRemoteBoot OBJECT-TYPE
--                              SYNTAX  OCTET STRING (SIZE(0..256))
--                              ACCESS  read-write
--                              STATUS  mandatory
--                              DESCRIPTION
--                              "The temporary directory used for remote booting."
--                              ::= { remoteAccessIdsEntry 9 }

      -- 51.1.4.1.4.2
      remoteAccessUserAuthorityLevelTable  OBJECT-TYPE
                            SYNTAX  SEQUENCE OF RemoteAccessUserAuthorityLevelEntry
                            ACCESS  not-accessible
                            STATUS  mandatory
                            DESCRIPTION
                            "Table of user authority level profiles."
                            ::= {  remoteAccessIds 2 }
                            
      remoteAccessUserAuthorityLevelEntry  OBJECT-TYPE
                            SYNTAX RemoteAccessUserAuthorityLevelEntry
                            ACCESS  not-accessible
                            STATUS  mandatory
                            DESCRIPTION
                            "User authority level entries."
                            INDEX { ualIndex }
                            ::= { remoteAccessUserAuthorityLevelTable 1 }
                            
      RemoteAccessUserAuthorityLevelEntry ::= SEQUENCE { 
                   ualIndex INTEGER(0..255),
                   ualId OCTET STRING (SIZE(0..16)),
                   ualSupervisor INTEGER,
                   ualReadOnly INTEGER,
                   ualAccountManagement INTEGER,
                   ualConsoleAccess INTEGER,
                   ualConsoleAndVirtualMediaAccess INTEGER,
                   ualServerPowerAccess INTEGER,
                   ualAllowClearLog INTEGER,
                   ualAdapterBasicConfig INTEGER,
                   ualAdapterNetworkAndSecurityConfig INTEGER,
                   ualAdapterAdvancedConfig INTEGER
      }
      
      ualIndex  OBJECT-TYPE
                    SYNTAX  INTEGER(0..255) 
                    ACCESS  read-only
                    STATUS  mandatory
                    DESCRIPTION
                    "Index for User Authority Level entry."  
                    ::= { remoteAccessUserAuthorityLevelEntry 1 }

      ualId    OBJECT-TYPE
                    SYNTAX  OCTET STRING (SIZE(0..16))
                    ACCESS  read-only
                    STATUS  mandatory
                    DESCRIPTION
                    "User ID"
                    ::= { remoteAccessUserAuthorityLevelEntry 2 }

      ualSupervisor OBJECT-TYPE
                    SYNTAX  INTEGER {
                       disabled(0),
                       enabled(1)
                    }
                    ACCESS  read-write
                    STATUS  mandatory
                    DESCRIPTION
                    "User has no restrictions."
                    ::= { remoteAccessUserAuthorityLevelEntry 3 }

      ualReadOnly OBJECT-TYPE
                    SYNTAX  INTEGER {
                       disabled(0),
                       enabled(1)
                    }
                    ACCESS  read-write
                    STATUS  mandatory
                    DESCRIPTION
                    "User has only read-only access, and cannot perform any save, modify, 
                    clear, or state affecting operations (eg. restart MM, restore defaults, 
                    upgrade the firmware, etc.)."
                    ::= { remoteAccessUserAuthorityLevelEntry 4 }

      ualAccountManagement OBJECT-TYPE
                    SYNTAX  INTEGER {
                       disabled(0),
                       enabled(1)
                    }
                    ACCESS  read-write
                    STATUS  mandatory
                    DESCRIPTION
                    "User can add/modify/delete users and change the global login settings in 
                    the Login Profiles panel."
                    ::= { remoteAccessUserAuthorityLevelEntry 5 }

      ualConsoleAccess OBJECT-TYPE
                    SYNTAX  INTEGER {
                       disabled(0),
                       enabled(1)
                    }
                    ACCESS  read-write
                    STATUS  mandatory
                    DESCRIPTION
                    "User can access the remote console."
                    ::= { remoteAccessUserAuthorityLevelEntry 6 }

      ualConsoleAndVirtualMediaAccess OBJECT-TYPE
                    SYNTAX  INTEGER {
                       disabled(0),
                       enabled(1)
                    }
                    ACCESS  read-write
                    STATUS  mandatory
                    DESCRIPTION
                    "User can access both the remote console and the virtual media feature."
                    ::= { remoteAccessUserAuthorityLevelEntry 7 }

      ualServerPowerAccess OBJECT-TYPE
                    SYNTAX  INTEGER {
                       disabled(0),
                       enabled(1)
                    }
                    ACCESS  read-write
                    STATUS  mandatory
                    DESCRIPTION
                    "User can access the power on and restart functions for the remote server. 
                    These functions are available via the Power/Restart panel."
                    ::= { remoteAccessUserAuthorityLevelEntry 8 }

      ualAllowClearLog OBJECT-TYPE
                    SYNTAX  INTEGER {
                       disabled(0),
                       enabled(1)
                    }
                    ACCESS  read-write
                    STATUS  mandatory
                    DESCRIPTION
                    "User can clear the event logs. Everyone can look at the 
                    event logs, but this particular permission is required to clear the logs."
                    ::= { remoteAccessUserAuthorityLevelEntry 9 }
                    
      ualAdapterBasicConfig OBJECT-TYPE
                    SYNTAX  INTEGER {
                       disabled(0),
                       enabled(1)
                    }
                    ACCESS  read-write
                    STATUS  mandatory
                    DESCRIPTION
                    "User can modify configuration parameters in the System Settings and Alerts 
                    panels."
                    ::= { remoteAccessUserAuthorityLevelEntry 10 }
                    
      ualAdapterNetworkAndSecurityConfig OBJECT-TYPE
                    SYNTAX  INTEGER {
                       disabled(0),
                       enabled(1)
                    }
                    ACCESS  read-write
                    STATUS  mandatory
                    DESCRIPTION
                    "User can modify configuration parameters in the Security, Network Protocols, 
                    Network Interface, Port Assignments, and Serial Port panels."
                    ::= { remoteAccessUserAuthorityLevelEntry 11 }
                    
      ualAdapterAdvancedConfig OBJECT-TYPE
                    SYNTAX  INTEGER {
                       disabled(0),
                       enabled(1)
                    }
                    ACCESS  read-write
                    STATUS  mandatory
                    DESCRIPTION
                    "User has no restrictions when configuring the adapter. In addition, the 
                    user is said to have administrative access to the RSA, meaning that the 
                    user can also perform the following advanced functions: firmware upgrades, 
                    PXE network boot, restore adapter factory defaults, modify and restore 
                    adapter configuration from a configuration file, and restart/reset the 
                    adapter."
                    ::= { remoteAccessUserAuthorityLevelEntry 12 }


      -- 51.2.4.1.4.3
      remoteAccessRBSroleTable  OBJECT-TYPE
                    SYNTAX  SEQUENCE OF RemoteAccessRBSroleEntry
                    ACCESS  not-accessible
                    STATUS  mandatory
                    DESCRIPTION
                    "Table of RBS User Role profiles."
                    ::= {  remoteAccessIds 3 }

      remoteAccessRBSroleEntry  OBJECT-TYPE
                    SYNTAX RemoteAccessRBSroleEntry
                    ACCESS  not-accessible
                    STATUS  mandatory
                    DESCRIPTION
                    "User Role entries."
                    INDEX { roleIndex }
                    ::= { remoteAccessRBSroleTable 1 }

      RemoteAccessRBSroleEntry ::= SEQUENCE {
                    roleIndex INTEGER(0..255),
                    roleId OCTET STRING (SIZE(0..16)),
                    rbsSupervisor INTEGER,
                    rbsOperator INTEGER,
                    rbsChassisOperator INTEGER,
                    rbsChassisAccountManagement INTEGER,
                    rbsChassisLogManagement INTEGER,
                    rbsChassisConfiguration INTEGER,
                    rbsChassisAdministration INTEGER,             
                    rbsBladeOperator INTEGER,
                    rbsBladeRemotePresence INTEGER,
                    rbsBladeConfiguration INTEGER,
                    rbsBladeAdministration INTEGER,
                    rbsSwitchModuleOperator INTEGER,
                    rbsSwitchModuleConfiguration INTEGER,
                    rbsSwitchModuleAdministration INTEGER
      }


      roleIndex  OBJECT-TYPE
                    SYNTAX  INTEGER(0..255)
                    ACCESS  read-only
                    STATUS  mandatory
                    DESCRIPTION
                    "Index for RBS User Role entry."
                    ::= { remoteAccessRBSroleEntry 1 }

      roleId    OBJECT-TYPE
                    SYNTAX  OCTET STRING (SIZE(0..16))
                    ACCESS  read-only
                    STATUS  mandatory
                    DESCRIPTION
                    "User ID"
                    ::= { remoteAccessRBSroleEntry 2 }

      rbsSupervisor OBJECT-TYPE
                    SYNTAX  INTEGER {
                       disabled(0),
                       enabled(1)
                    }
                    ACCESS  read-write
                    STATUS  mandatory
                    DESCRIPTION
                    "User has no restrictions."
                    ::= { remoteAccessRBSroleEntry 3 }

      rbsOperator OBJECT-TYPE
                    SYNTAX  INTEGER {
                       disabled(0),
                       enabled(1)
                    }
                    ACCESS  read-write
                    STATUS  mandatory
                    DESCRIPTION
                    "User has only operator access, and cannot perform
                    any save, modify, clear, or state affecting operations
                    (eg. restart MM, restore defaults, upgrade the firmware,
                    etc.)."
                    ::= { remoteAccessRBSroleEntry 4 }

      rbsChassisOperator OBJECT-TYPE
                    SYNTAX  INTEGER {
                       disabled(0),
                       enabled(1)
                    }
                    ACCESS  read-write
                    STATUS  mandatory
                    DESCRIPTION
                    "User has ability to browse status and properties of
                    chassis components (MM, blowers, midplane, power modules,
                    media tray."
                    ::= { remoteAccessRBSroleEntry 5 }


      rbsChassisAccountManagement OBJECT-TYPE
                    SYNTAX  INTEGER {
                       disabled(0),
                       enabled(1)
                    }
                    ACCESS  read-write
                    STATUS  mandatory
                    DESCRIPTION
                    "User can add/modify/delete users and change the
                    global login settings."
                    ::= { remoteAccessRBSroleEntry 6 }

      rbsChassisLogManagement OBJECT-TYPE
                    SYNTAX  INTEGER {
                       disabled(0),
                       enabled(1)
                    }             
                    ACCESS  read-write
                    STATUS  mandatory
                    DESCRIPTION
                    "User has ability to clear the MM event log and to change
                    log policy settings."
                    ::= { remoteAccessRBSroleEntry 7 }

      rbsChassisConfiguration OBJECT-TYPE
                    SYNTAX  INTEGER {
                       disabled(0),
                       enabled(1)
                    }
                    ACCESS  read-write
                    STATUS  mandatory
                    DESCRIPTION
                    "User can modify and save any chassis configuration
                    parameter (except user profiles and event log settings.)"
                    ::= { remoteAccessRBSroleEntry 8 }

      rbsChassisAdministration OBJECT-TYPE
                    SYNTAX  INTEGER {
                       disabled(0),
                       enabled(1)
                    }
                    ACCESS  read-write
                    STATUS  mandatory
                    DESCRIPTION
                    "User has ability to backup or restore MM configuration,
                    do MM firmware updates, restore MM factory defaults
                    configuration, or restart the MM.)"
                    ::= { remoteAccessRBSroleEntry 9 }

      rbsBladeOperator OBJECT-TYPE
                    SYNTAX  INTEGER {
                       disabled(0),
                       enabled(1)
                    }
                    ACCESS  read-write
                    STATUS  mandatory
                    DESCRIPTION
                    "User has ability to browse status and properties of
                    blades."
                    ::= { remoteAccessRBSroleEntry 10 }

      rbsBladeRemotePresence OBJECT-TYPE
                    SYNTAX  INTEGER {
                       disabled(0),
                       enabled(1)
                    }
                    ACCESS  read-write
                    STATUS  mandatory
                    DESCRIPTION
                    "User has ability to access the Remote Control web panel
                    and the functions provided on the panel: remote console
                    (KVM) and remote disk. The ability to issue the CLI
                    console command to start an SOL session to a blade will
                    also require this authority."
                    ::= { remoteAccessRBSroleEntry 11 }

      rbsBladeConfiguration OBJECT-TYPE
                    SYNTAX  INTEGER {
                       disabled(0),
                       enabled(1)
                    }
                    ACCESS  read-write
                    STATUS  mandatory
                    DESCRIPTION
                    "User can modify and save any blade configuration
                    parameter."
                    ::= { remoteAccessRBSroleEntry 12 }

      rbsBladeAdministration OBJECT-TYPE
                    SYNTAX  INTEGER {
                       disabled(0),
                       enabled(1)
                    }
                    ACCESS  read-write
                    STATUS  mandatory
                    DESCRIPTION
                    "User can power on/off and restart blades, activate
                    standby blade servers, do firmware updates."
                    ::= { remoteAccessRBSroleEntry 13 }

      rbsSwitchModuleOperator OBJECT-TYPE
                    SYNTAX  INTEGER {
                       disabled(0),
                       enabled(1)
                    }
                    ACCESS  read-write
                    STATUS  mandatory
                    DESCRIPTION
                    "User has ability to browse status and properties of
                    I/O modules."
                    ::= { remoteAccessRBSroleEntry 14 }

      rbsSwitchModuleConfiguration OBJECT-TYPE
                    SYNTAX  INTEGER {
                       disabled(0),
                       enabled(1)
                    }
                    ACCESS  read-write
                    STATUS  mandatory
                    DESCRIPTION
                    "User can modify the switch module configuration
                    parameters on the Switch Management."
                    ::= { remoteAccessRBSroleEntry 15 }

      rbsSwitchModuleAdministration OBJECT-TYPE
                    SYNTAX  INTEGER {
                       disabled(0),
                       enabled(1)
                    }
                    ACCESS  read-write
                    STATUS  mandatory
                    DESCRIPTION
                    "User can power on/off and restart the switch modules,
                    and update switch module firmware."
                    ::= { remoteAccessRBSroleEntry 16 }


      -- 51.2.4.1.4.4
      remoteAccessRBSscopeTable  OBJECT-TYPE
                    SYNTAX  SEQUENCE OF RemoteAccessRBSscopeEntry
                    ACCESS  not-accessible
                    STATUS  mandatory
                    DESCRIPTION
                    "Table of RBS User Scope profiles."
                    ::= {  remoteAccessIds 4 }

      remoteAccessRBSscopeEntry  OBJECT-TYPE
                    SYNTAX RemoteAccessRBSscopeEntry
                    ACCESS  not-accessible
                    STATUS  mandatory
                    DESCRIPTION
                    "User Scope entries."
                    INDEX { scopeIndex }
                    ::= { remoteAccessRBSscopeTable 1 }

      RemoteAccessRBSscopeEntry ::= SEQUENCE {
                    scopeIndex INTEGER(0..255),
                    scopeId OCTET STRING (SIZE(0..16)),
                    rbsChassis INTEGER,
                    rbsBlade1 INTEGER,
                    rbsBlade2 INTEGER,
                    rbsBlade3 INTEGER,
                    rbsBlade4 INTEGER,
                    rbsBlade5 INTEGER,
                    rbsBlade6 INTEGER,
                    rbsBlade7 INTEGER,
                    rbsBlade8 INTEGER,
                    rbsBlade9 INTEGER,
                    rbsBlade10 INTEGER,
                    rbsBlade11 INTEGER,
                    rbsBlade12 INTEGER,
                    rbsBlade13 INTEGER,
                    rbsBlade14 INTEGER,
                    rbsSwitch1 INTEGER,
                    rbsSwitch2 INTEGER,
                    rbsSwitch3 INTEGER,
                    rbsSwitch4 INTEGER  
      }


      scopeIndex  OBJECT-TYPE
                    SYNTAX  INTEGER(0..255)
                    ACCESS  read-only
                    STATUS  mandatory
                    DESCRIPTION
                    "Index for RBS User Scope Entry."
                    ::= { remoteAccessRBSscopeEntry 1 }

      scopeId    OBJECT-TYPE
                    SYNTAX  OCTET STRING (SIZE(0..16))
                    ACCESS  read-only
                    STATUS  mandatory
                    DESCRIPTION
                    "User ID"
                    ::= { remoteAccessRBSscopeEntry 2 }

      rbsChassis OBJECT-TYPE
                    SYNTAX  INTEGER {
                       disabled(0),
                       enabled(1)
                    }
                    ACCESS  read-write
                    STATUS  mandatory
                    DESCRIPTION
                    "User has access to the MM and chassis functions."
                    ::= { remoteAccessRBSscopeEntry 3 }

      rbsBlade1 OBJECT-TYPE
                    SYNTAX  INTEGER {
                       disabled(0),
                       enabled(1)
                    }
                    ACCESS  read-write
                    STATUS  mandatory
                    DESCRIPTION
                    "User has access to the blade in slot 1."
                    ::= { remoteAccessRBSscopeEntry 4 }

      rbsBlade2 OBJECT-TYPE
                    SYNTAX  INTEGER {
                       disabled(0),
                       enabled(1)
                    }
                    ACCESS  read-write
                    STATUS  mandatory
                    DESCRIPTION
                    "User has access to the blade in slot 2."
                    ::= { remoteAccessRBSscopeEntry 5 }


      rbsBlade3 OBJECT-TYPE
                    SYNTAX  INTEGER {
                       disabled(0),
                       enabled(1)
                    }
                    ACCESS  read-write
                    STATUS  mandatory
                    DESCRIPTION
                    "User has access to the blade in slot 3."
                    ::= { remoteAccessRBSscopeEntry 6 }

      rbsBlade4 OBJECT-TYPE
                    SYNTAX  INTEGER {
                       disabled(0),
                       enabled(1)
                    }
                    ACCESS  read-write
                    STATUS  mandatory
                    DESCRIPTION
                    "User has access to the blade in slot 4."
                    ::= { remoteAccessRBSscopeEntry 7 }

      rbsBlade5 OBJECT-TYPE
                    SYNTAX  INTEGER {
                       disabled(0),
                       enabled(1)
                    }
                    ACCESS  read-write
                    STATUS  mandatory
                    DESCRIPTION
                    "User has access to the blade in slot 5."
                    ::= { remoteAccessRBSscopeEntry 8 }

      rbsBlade6 OBJECT-TYPE
                    SYNTAX  INTEGER {
                       disabled(0),
                       enabled(1)
                    }
                    ACCESS  read-write
                    STATUS  mandatory
                    DESCRIPTION
                    "User has access to the blade in slot 6."
                    ::= { remoteAccessRBSscopeEntry 9 }

      rbsBlade7 OBJECT-TYPE
                    SYNTAX  INTEGER {
                       disabled(0),
                       enabled(1)
                    }
                    ACCESS  read-write
                    STATUS  mandatory
                    DESCRIPTION
                    "User has access to the blade in slot 7."
                    ::= { remoteAccessRBSscopeEntry 10 }


      rbsBlade8 OBJECT-TYPE
                    SYNTAX  INTEGER {
                       disabled(0),
                       enabled(1)
                    }
                    ACCESS  read-write
                    STATUS  mandatory
                    DESCRIPTION
                    "User has access to the blade in slot 8."
                    ::= { remoteAccessRBSscopeEntry 11 }

      rbsBlade9 OBJECT-TYPE
                    SYNTAX  INTEGER {
                       disabled(0),
                       enabled(1)
                    }
                    ACCESS  read-write
                    STATUS  mandatory
                    DESCRIPTION
                    "User has access to the blade in slot 9."
                    ::= { remoteAccessRBSscopeEntry 12 }

      rbsBlade10 OBJECT-TYPE
                    SYNTAX  INTEGER {
                       disabled(0),
                       enabled(1)
                    }
                    ACCESS  read-write
                    STATUS  mandatory
                    DESCRIPTION
                    "User has access to the blade in slot 10."
                    ::= { remoteAccessRBSscopeEntry 13 }

      rbsBlade11 OBJECT-TYPE
                    SYNTAX  INTEGER {
                       disabled(0),
                       enabled(1)
                    }
                    ACCESS  read-write
                    STATUS  mandatory
                    DESCRIPTION
                    "User has access to the blade in slot 11."
                    ::= { remoteAccessRBSscopeEntry 14 }

      rbsBlade12 OBJECT-TYPE
                    SYNTAX  INTEGER {
                       disabled(0),
                       enabled(1)
                    }
                    ACCESS  read-write
                    STATUS  mandatory
                    DESCRIPTION
                    "User has access to the blade in slot 12."
                    ::= { remoteAccessRBSscopeEntry 15 }


      rbsBlade13 OBJECT-TYPE
                    SYNTAX  INTEGER {
                       disabled(0),
                       enabled(1)
                    }
                    ACCESS  read-write
                    STATUS  mandatory
                    DESCRIPTION
                    "User has access to the blade in slot 13."
                    ::= { remoteAccessRBSscopeEntry 16 }

      rbsBlade14 OBJECT-TYPE
                    SYNTAX  INTEGER {
                       disabled(0),
                       enabled(1)
                    }
                    ACCESS  read-write
                    STATUS  mandatory
                    DESCRIPTION
                    "User has access to the blade in slot 14."
                    ::= { remoteAccessRBSscopeEntry 17 }

      rbsSwitch1 OBJECT-TYPE
                    SYNTAX  INTEGER {
                       disabled(0),
                       enabled(1)
                    }
                    ACCESS  read-write
                    STATUS  mandatory
                    DESCRIPTION
                    "User has access to switch module 1."
                    ::= { remoteAccessRBSscopeEntry 18 }

      rbsSwitch2 OBJECT-TYPE
                    SYNTAX  INTEGER {
                       disabled(0),
                       enabled(1)
                    }
                    ACCESS  read-write
                    STATUS  mandatory
                    DESCRIPTION
                    "User has access to switch module 2."
                    ::= { remoteAccessRBSscopeEntry 19 }

      rbsSwitch3 OBJECT-TYPE
                    SYNTAX  INTEGER {
                       disabled(0),
                       enabled(1)
                    }
                    ACCESS  read-write
                    STATUS  mandatory
                    DESCRIPTION
                    "User has access to switch module 3."
                    ::= { remoteAccessRBSscopeEntry 20 }

      rbsSwitch4 OBJECT-TYPE
                    SYNTAX  INTEGER {
                       disabled(0),
                       enabled(1)
                    }
                    ACCESS  read-write
                    STATUS  mandatory
                    DESCRIPTION
                    "User has access to switch module 4."
                    ::= { remoteAccessRBSscopeEntry 21 }
                    
    -- ********************************************************************************
    -- Remote Alert types
    -- ********************************************************************************
    -- 4.2
    remoteAlerts  OBJECT IDENTIFIER ::= { configureSP 2 }

     -- ********************************************************************************
     -- Remote Alert Critical Error types
     -- ********************************************************************************
     -- 4.2.1
     remoteAlertsCrit  OBJECT IDENTIFIER ::= { remoteAlerts 1 }

      -- 4.2.1.1
      critTemp     OBJECT-TYPE
                   SYNTAX  INTEGER {
                     disabled(0),
                     enabled(1)
                   }
                   ACCESS  read-write
                   STATUS  mandatory
                   DESCRIPTION
                   "Generate an alert if any of the monitored temperature sensors
                   in the system exceed their critical threshold.

                   Note: If a critical Temperature condition is detected,
                   the server will automatically be shut down and powered off
                   whether this object is enabled or not."
                   ::= { remoteAlertsCrit 1 }
      
      -- 4.2.1.2             
      critVolt     OBJECT-TYPE
                   SYNTAX  INTEGER {
                     disabled(0),
                     enabled(1)
                   }
                   ACCESS  read-write
                   STATUS  mandatory
                   DESCRIPTION
                   "Generate a alert if any of the monitored power supply sensors 
                   in the system fall outside their specified critical 
                   operational range.
                   
                   Note: If a critical voltage condition is detected, 
 	           the server will automatically be shut down and powered off 
 	           whether this object is enabled or not."
                   ::= { remoteAlertsCrit 2 }


      -- 4.2.1.4
      critMultiBlower OBJECT-TYPE
                   SYNTAX  INTEGER {
                     disabled(0),
                     enabled(1)
                   }
                   ACCESS  read-write
                   STATUS  mandatory
                   DESCRIPTION
                   "Generate an alert if multiple blowers used for cooling the system fail."
                   ::= { remoteAlertsCrit 4 }

      -- 4.2.1.5
      critPower    OBJECT-TYPE
                   SYNTAX  INTEGER {
                     disabled(0),
                     enabled(1)
                   }
                   ACCESS  read-write
                   STATUS  mandatory
                   DESCRIPTION
                   "Generate an alert if any of the system power supplies fail."
                   ::= { remoteAlertsCrit 5 }

      -- 4.2.1.6
      critHardDrive OBJECT-TYPE
                   SYNTAX  INTEGER {
                     disabled(0),
                     enabled(1)
                   }
                   ACCESS  read-write
                   STATUS  mandatory
                   DESCRIPTION
                   "Generate an alert if any of hard disk drives fail."
                   ::= { remoteAlertsCrit 6 }

      -- 4.2.1.7
      critVRM     OBJECT-TYPE
                   SYNTAX  INTEGER {
                     disabled(0),
                     enabled(1)
                   }
                   ACCESS  read-write
                   STATUS  mandatory
                   DESCRIPTION
                   "Generate an alert if any of VRM (voltage regulator modules) fail."
                   ::= { remoteAlertsCrit 7 }


      -- 4.2.1.8
      critMultipleSwitchModule  OBJECT-TYPE
                   SYNTAX  INTEGER {
                     disabled(0),
                     enabled(1)
                   }
                   ACCESS  read-write
                   STATUS  mandatory
                   DESCRIPTION
                   "Generate an alert if all switch modules fail or are removed."
                   ::= { remoteAlertsCrit 8 }

      -- 4.2.1.9
      critInvalidConfig  OBJECT-TYPE
                   SYNTAX  INTEGER {
                     disabled(0),
                     enabled(1)
                   }
                   ACCESS  read-write
                   STATUS  mandatory
                   DESCRIPTION
                   "Generate an alert if the hardware configuration is incompatible."
                   ::= { remoteAlertsCrit 9 }




     -- ********************************************************************************
     -- Remote Alert Warning(non-critical) Error types
     -- ********************************************************************************
     -- 4.2.2
     remoteAlertsNonCrit  OBJECT IDENTIFIER ::= { remoteAlerts 2 }

      -- 4.2.2.2
      warnSingleBlower OBJECT-TYPE
                    SYNTAX  INTEGER {
                      disabled(0),
                      enabled(1)
                    }
                    ACCESS  read-write
                    STATUS  mandatory
                    DESCRIPTION
                    "Generate an alert if one blower used for cooling the system fails."
                    ::= { remoteAlertsNonCrit 2 }

      -- 4.2.2.3
      warnTemp     OBJECT-TYPE
                   SYNTAX  INTEGER {
                     disabled(0),
                     enabled(1)
                   }
                   ACCESS  read-write
                   STATUS  mandatory
                   DESCRIPTION
                   "Generate an alert if any of the monitored temperature sensors
                   in the system exceed their warning threshold."
                   ::= { remoteAlertsNonCrit 3 }

      -- 4.2.2.4
      warnVoltage  OBJECT-TYPE
                   SYNTAX  INTEGER {
                     disabled(0),
                     enabled(1)
                   }
                   ACCESS  read-write
                   STATUS  mandatory
                   DESCRIPTION
                   "Generate an alert if any of the monitored power supply sensors
                   in the system fall outside their specified warning operational range."
                   ::= { remoteAlertsNonCrit 4 }

      -- 4.2.2.6
      warnRedundantModule  OBJECT-TYPE
                   SYNTAX  INTEGER {
                     disabled(0),
                     enabled(1)
                   }
                   ACCESS  read-write
                   STATUS  mandatory
                   DESCRIPTION
                   "Generate an alert if any of the switch modules or management
                   modules is failing or removed."
                   ::= { remoteAlertsNonCrit 6 }

      -- 4.2.2.7
      warnMediaTrayKVMSwitch  OBJECT-TYPE
                   SYNTAX  INTEGER {
                     disabled(0),
                     enabled(1)
                   }
                   ACCESS  read-write
                   STATUS  mandatory
                   DESCRIPTION
                   "Generate an alert if the system detects a Media Tray or KVM
                   switching failure."
                   ::= {  remoteAlertsNonCrit 7 }


     -- ********************************************************************************
     -- Remote Alert System Error types
     -- ********************************************************************************
     -- 4.2.3
     remoteAlertsSystem  OBJECT IDENTIFIER ::= { remoteAlerts 3 }


      -- 4.2.3.4
      systemPowerOff OBJECT-TYPE
                   SYNTAX  INTEGER {
                     disabled(0),
                     enabled(1)
                   }
                   ACCESS  read-write
                   STATUS  mandatory
                   DESCRIPTION
                   "Generate an alert if the system is powered off."
                   ::= { remoteAlertsSystem 4 }

      -- 4.2.3.5
      systemPowerOn  OBJECT-TYPE
                   SYNTAX  INTEGER {
                     disabled(0),
                     enabled(1)
                   }
                   ACCESS  read-write
                   STATUS  mandatory
                   DESCRIPTION
                   "Generate a alert if the system is powered on."
                   ::= { remoteAlertsSystem 5 }

      -- 4.2.3.8
      systemPFA    OBJECT-TYPE
                   SYNTAX  INTEGER {
                     disabled(0),
                     enabled(1)
                   }
                   ACCESS  read-write
                   STATUS  mandatory
                   DESCRIPTION
                   "Generate a alert if the system hardware detects a Predictive
                   Failure Analysis(PFA) on PFA enabled hardware."
                   ::= {  remoteAlertsSystem 8 }

      -- 4.2.3.10
      systemInventory  OBJECT-TYPE
                   SYNTAX  INTEGER {
                     disabled(0),
                     enabled(1)
                   }
                   ACCESS  read-write
                   STATUS  mandatory
                   DESCRIPTION
                   "Generate an alert if the a processor blade or media tray is
                   added or removed."
                   ::= {  remoteAlertsSystem 10 }

      -- 4.2.3.11
      systemLog75PctFull  OBJECT-TYPE
                   SYNTAX  INTEGER {
                     disabled(0),
                     enabled(1)
                   }
                   ACCESS  read-write
                   STATUS  mandatory
                   DESCRIPTION
                   "Generate an alert if the system log reaches 75% full."
                   ::= {  remoteAlertsSystem 11 }

      -- 4.2.3.12
      networkChangeNotification OBJECT-TYPE
                   SYNTAX  INTEGER {
                     disabled(0),
                     enabled(1)
                   }
                   ACCESS  read-write
                   STATUS  mandatory
                   DESCRIPTION
                   "Generate an alert if the MM has restarted and the internal
                   network has initialized successfully, or if an IP address
                   change via a source other than the management module."
                   ::= {  remoteAlertsSystem 12 }

      -- 4.2.3.13
      systemBladeThrottling  OBJECT-TYPE
                   SYNTAX  INTEGER {
                     disabled(0),
                     enabled(1)
                   }
                   ACCESS  read-write
                   STATUS  mandatory
                   DESCRIPTION
                   "Generate an alert if any of the server blades are throttling."
                   ::= {  remoteAlertsSystem 13 }

      -- 4.2.3.14
      systemPowerManagement  OBJECT-TYPE
                   SYNTAX  INTEGER {
                     disabled(0),
                     enabled(1)
                   }
                   ACCESS  read-write
                   STATUS  mandatory
                   DESCRIPTION
                   "Generate an alert if the system detects a power oversubscription 
                   condition or power supply mismatch in a power domain." 
                   ::= {  remoteAlertsSystem 14 }
     
     -- ********************************************************************************
     -- Environmental Monitor Thresholds
     -- ********************************************************************************
     -- 4.3.2
     monitorThresholds  OBJECT IDENTIFIER ::= { monitors 20 }

      -- ********************************************************************************
      -- Temperature Thresholds
      -- ********************************************************************************
      -- 4.3.2.1
--    tempThresholds  OBJECT IDENTIFIER ::= { monitorThresholds 1 }
--
--
       -- 4.3.2.1.1
--     generalSystemTempThresholds OBJECT IDENTIFIER ::= { tempThresholds 1 }
--
--
--      generalTempThresholdsTable  OBJECT-TYPE
--                            SYNTAX  SEQUENCE OF GeneralTempThresholdsEntry
--                            ACCESS  not-accessible
--                            STATUS  mandatory
--                            DESCRIPTION
--                            "Table of General Temperature threshold entries.
--                            Has information about the Planar temperature and
--                            System Ambient temperature."
--                            ::= {  generalSystemTempThresholds 1 }
--
--      generalTempThresholdsEntry  OBJECT-TYPE
--                            SYNTAX  GeneralTempThresholdsEntry
--                            ACCESS  not-accessible
--                            STATUS  mandatory
--                            DESCRIPTION
--                            "General Temperature threshold entries."
--                            INDEX { generalTempThresholdEntryIndex }
--                            ::= { generalTempThresholdsTable 1 }
--
--      GeneralTempThresholdsEntry ::= SEQUENCE {
--                   generalTempThresholdEntryIndex INTEGER(0..255),
--                   generalTempThresholdEntryName OCTET STRING (SIZE(0..16)),
--                   generalTempThresholdEntryCurrentValue OCTET STRING,
--                   generalTempThresholdEntryHardShutdownValue OCTET STRING,
--                   generalTempThresholdEntrySoftShutdownValue OCTET STRING,
--                   generalTempThresholdEntryWarningValue OCTET STRING,
--                   generalTempThresholdEntryWarningResetValue OCTET STRING
--      }
--
--
--      generalTempThresholdEntryIndex  OBJECT-TYPE
--                                SYNTAX  INTEGER(0..255)
--                                ACCESS  read-only
--                                STATUS  mandatory
--                                DESCRIPTION
--                                "Index for a general temperature threshold entry."
--                                ::= { generalTempThresholdsEntry 1 }
--
--      generalTempThresholdEntryName  OBJECT-TYPE
--                                SYNTAX  OCTET STRING (SIZE(0..16))
--                                ACCESS  read-only
--                                STATUS  mandatory
--                                DESCRIPTION
--                                "Null terminated string that
--                                contains the individual temperature monitor's name."
--                                ::= { generalTempThresholdsEntry 2 }
--
--      generalTempThresholdEntryCurrentValue OBJECT-TYPE
--                                  SYNTAX  OCTET STRING
--                                  ACCESS  read-only
--                                  STATUS  mandatory
--                                  DESCRIPTION
--                                  "Temperature in degrees centigrade(C).
--                                  An octet string expressed as 'sddd.dd Centigrade' where:
--                                  s is the sign ('-' for negative or blank space for positive)
--                                  d is a decimal digit or blank space for a leading zero.
--                                  The string 'Not Readable!' indicates that the given monitor
--                                  is not supported on this system."
--                                  ::= { generalTempThresholdsEntry 3 }
--
        -- 4.3.2.1.1.1
--      generalTempThresholdEntryHardShutdownValue OBJECT-TYPE
--                                  SYNTAX  OCTET STRING
--                                  ACCESS  read-only
--                                  STATUS  mandatory
--                                  DESCRIPTION
--                                  "Temperature in degrees centigrade(C).
--                                  If the component's temperature rises above this value the
--                                  system will be powered off immediately.
--                                  If enabled, a critical alert/event will be generated.
--                                  An octet string expressed as 'sddd.dd Centigrade' where:
--                                  s is the sign ('-' for negative or blank space for positive)
--                                  d is a decimal digit or blank space for a leading zero.
--                                  The string 'Not Readable!' indicates that the given monitor
--                                  is not supported on this system."
--                                  ::= { generalTempThresholdsEntry 4 }
--
        -- 4.3.2.1.1.2
--      generalTempThresholdEntrySoftShutdownValue OBJECT-TYPE
--                                  SYNTAX  OCTET STRING
--                                  ACCESS  read-only
--                                  STATUS  mandatory
--                                  DESCRIPTION
--                                  "Temperature in degrees centigrade(C).
--                                  If the component's temperature rises above this value the
--                                  system will be powered off after the O/S is shut down.
--                                  If enabled, a critical alert/event is generated.
--                                  An octet string expressed as 'sddd.dd Centigrade' where:
--                                  s is the sign ('-' for negative or blank space for positive)
--                                  d is a decimal digit or blank space for a leading zero.
--                                  The string 'Not Readable!' indicates that the given monitor
--                                  is not supported on this system."
--                                  ::= { generalTempThresholdsEntry 5 }
--
        -- 4.3.2.1.1.3
--      generalTempThresholdEntryWarningValue OBJECT-TYPE
--                                  SYNTAX  OCTET STRING
--                                  ACCESS  read-only
--                                  STATUS  mandatory
--                                  DESCRIPTION
--                                  "Temperature in degrees centigrade(C).
--                                  If the temperature rises above this value a warning alert/event
--                                  if enabled will be generated.
--                                  An octet string expressed as 'sddd.dd Centigrade' where:
--                                  s is the sign ('-' for negative or blank space for positive)
--                                  d is a decimal digit or blank space for a leading zero.
--                                  The string 'Not Readable!' indicates that the given monitor
--                                  is not supported on this system."
--                                  ::= { generalTempThresholdsEntry 6 }
--
        -- 4.3.2.1.1.4
--      generalTempThresholdEntryWarningResetValue OBJECT-TYPE
--                                  SYNTAX  OCTET STRING
--                                  ACCESS  read-only
--                                  STATUS  mandatory
--                                  DESCRIPTION
--                                  "Temperature in degrees centigrade(C).
--                                  If the temperature rises above this value and
--                                  if a warning alert/event had previously been
--                                  created then the alert/event will be reset.
--                                  An octet string expressed as 'sddd.dd Centigrade' where:
--                                  s is the sign ('-' for negative or blank space for positive)
--                                  d is a decimal digit or blank space for a leading zero.
--                                  The string 'Not Readable!' indicates that the given monitor
--                                  is not supported on this system."
--                                  ::= { generalTempThresholdsEntry 7 }
--
--

      -- ********************************************************************************
      -- Voltage Thresholds
      -- ********************************************************************************
      -- 4.3.2.2
      voltageThresholds  OBJECT IDENTIFIER ::= { monitorThresholds 2 }

       voltageThresholdsTable  OBJECT-TYPE
                             SYNTAX  SEQUENCE OF VoltageThresholdsEntry
                             ACCESS  not-accessible
                             STATUS  mandatory
                             DESCRIPTION
                             "Table of voltage threshold entries.
                             
                             NOTE: This MIB is for BladeCenter only."
                             ::= {  voltageThresholds 1 }

       voltageThresholdsEntry  OBJECT-TYPE
                             SYNTAX VoltageThresholdsEntry
                             ACCESS  not-accessible
                             STATUS  mandatory
                             DESCRIPTION
                             "Voltage threshold entries.
                             
                             NOTE: This MIB is for BladeCenter only."
                             INDEX { voltageThresholdEntryIndex }
                             ::= { voltageThresholdsTable 1 }

       VoltageThresholdsEntry ::= SEQUENCE {
                    voltageThresholdEntryIndex INTEGER(0..255),
                    voltageThresholdEntryName OCTET STRING (SIZE(0..16)),
                    voltageThresholdEntryCurrentValue OCTET STRING,
--                  voltageThresholdEntryHardShutdownHighValue OCTET STRING,
--                  voltageThresholdEntrySoftShutdownHighValue OCTET STRING,
                    voltageThresholdEntryWarningHighValue OCTET STRING,
                    voltageThresholdEntryWarningResetHighValue OCTET STRING,
--                  voltageThresholdEntryHardShutdownLowValue OCTET STRING,
--                  voltageThresholdEntrySoftShutdownLowValue OCTET STRING,
                    voltageThresholdEntryWarningLowValue OCTET STRING,
                    voltageThresholdEntryWarningResetLowValue OCTET STRING
       }


       voltageThresholdEntryIndex  OBJECT-TYPE
                                 SYNTAX  INTEGER(0..255)
                                 ACCESS  read-only
                                 STATUS  mandatory
                                 DESCRIPTION
                                 "Index for voltage threshold entry."
                                 
                                 ::= { voltageThresholdsEntry 1 }

       -- 4.3.2.2.x
       voltageThresholdEntryName  OBJECT-TYPE
                                 SYNTAX  OCTET STRING (SIZE(0..16))
                                 ACCESS  read-only
                                 STATUS  mandatory
                                 DESCRIPTION
                                 "Voltage threshold entry null terminated string that
                                 contains the power supply's name, for example '+5V'."
                                 
                                 ::= { voltageThresholdsEntry 2 }

       -- 2.1.2.x
       voltageThresholdEntryCurrentValue OBJECT-TYPE
                                   SYNTAX  OCTET STRING
                                   ACCESS  read-only
                                   STATUS  mandatory
                                   DESCRIPTION
                                   "Voltage reading expressed in Volts(V).
                                   An octet string expressed as 'sdd.dd Volts' where:
                                   s is the sign ('-' for negative or '+' for positive)
                                   d is a decimal digit or blank space for a leading zero.
                                   The string 'Not Readable!' indicates that the given monitor
                                   is not supported on this system."
                                   
                                   ::= { voltageThresholdsEntry 3 }

       -- 4.3.2.2.x.1
--     voltageThresholdEntryHardShutdownHighValue OBJECT-TYPE
--                                 SYNTAX  OCTET STRING
--                                 ACCESS  read-only
--                                 STATUS  mandatory
--                                 DESCRIPTION
--                                 "Voltage threshold reading expressed in Volts(V).
--                                 If the voltage rises above this value the
--                                 system will be powered off immediately.
--                                 If enabled, a critical alert/event will be generated.
--                                 An octet string expressed as 'sdd.dd Volts' where:
--                                 s is the sign ('-' for negative or '+' for positive)
--                                 d is a decimal digit or blank space for a leading zero.
--                                 The string 'Not Readable!' indicates that the given monitor
--                                 is not supported on this system."
--                                 ::= { voltageThresholdsEntry 4 }
--
       -- 4.3.2.2.x.2
--     voltageThresholdEntrySoftShutdownHighValue OBJECT-TYPE
--                                 SYNTAX  OCTET STRING
--                                 ACCESS  read-only
--                                 STATUS  mandatory
--                                 DESCRIPTION
--                                 "Voltage threshold reading expressed in Volts(V).
--                                 If the voltage rises above this value, the system will
--                                 be powered off after the O/S is shut down.
--                                 If enabled, a critical alert/event is generated.
--                                 An octet string expressed as 'sdd.dd Volts' where:
--                                 s is the sign ('-' for negative or '+' for positive)
--                                 d is a decimal digit or blank space for a leading zero.
--                                 The string 'Not Readable!' indicates that the given monitor
--                                 is not supported on this system."
--                                 ::= { voltageThresholdsEntry 5 }

       -- 4.3.2.2.x.3
       voltageThresholdEntryWarningHighValue OBJECT-TYPE
                                   SYNTAX  OCTET STRING
                                   ACCESS  read-only
                                   STATUS  mandatory
                                   DESCRIPTION
                                   "Voltage threshold reading expressed in Volts(V).
                                   If the voltage rises above this value, a warning
                                   alert/event, if enabled, will be generated.
                                   An octet string expressed as 'sdd.dd Volts' where:
                                   s is the sign ('-' for negative or '+' for positive)
                                   d is a decimal digit or blank space for a leading zero.
                                   The string 'Not Readable!' indicates that the given monitor
                                   is not supported on this system."
                                   
                                   ::= { voltageThresholdsEntry 6 }

       -- 4.3.2.2.x.4
       voltageThresholdEntryWarningResetHighValue OBJECT-TYPE
                                   SYNTAX  OCTET STRING
                                   ACCESS  read-only
                                   STATUS  mandatory
                                   DESCRIPTION
                                   "Voltage threshold reading expressed in Volts(V).
                                   If the voltage rises above this value and
                                   if a warning alert/event had previously been
                                   created, then the alert/event will be reset.
                                   An octet string expressed as 'sdd.dd Volts' where:
                                   s is the sign ('-' for negative or '+' for positive)
                                   d is a decimal digit or blank space for a leading zero.
                                   The string 'Not Readable!' indicates that the given monitor
                                   is not supported on this system."
                                   
                                   ::= { voltageThresholdsEntry 7 }

       -- 4.3.2.2.x.5
--     voltageThresholdEntryHardShutdownLowValue OBJECT-TYPE
--                                 SYNTAX  OCTET STRING
--                                 ACCESS  read-only
--                                 STATUS  mandatory
--                                 DESCRIPTION
--                                 "Voltage threshold reading expressed in Volts(V).
--                                 If the voltage drops below this value, the
--                                 system will be powered off immediately.
--                                 If enabled, a critical alert/event will be generated.
--                                 An octet string expressed as 'sdd.dd Volts' where:
--                                 s is the sign ('-' for negative or '+' for positive)
--                                 d is a decimal digit or blank space for a leading zero.
--                                 The string 'Not Readable!' indicates that the given monitor
--                                 is not supported on this system."
--                                 ::= { voltageThresholdsEntry 8 }
--
       -- 4.3.2.2.x.6
--     voltageThresholdEntrySoftShutdownLowValue OBJECT-TYPE
--                                 SYNTAX  OCTET STRING
--                                 ACCESS  read-only
--                                 STATUS  mandatory
--                                 DESCRIPTION
--                                 "Voltage threshold reading expressed in Volts(V).
--                                 If the voltage drops below this value, the system will
--                                 be powered off after the O/S is shut down.
--                                 If enabled, a critical alert/event is generated.
--                                 An octet string expressed as 'sdd.dd Volts' where:
--                                 s is the sign ('-' for negative or '+' for positive)
--                                 d is a decimal digit or blank space for a leading zero.
--                                 The string 'Not Readable!' indicates that the given monitor
--                                 is not supported on this system."
--                                 ::= { voltageThresholdsEntry 9 }

       -- 4.3.2.2.x.7
       voltageThresholdEntryWarningLowValue OBJECT-TYPE
                                   SYNTAX  OCTET STRING
                                   ACCESS  read-only
                                   STATUS  mandatory
                                   DESCRIPTION
                                   "Voltage threshold reading expressed in Volts(V).
                                   If the voltage drops below this value, a warning
                                   alert/event, if enabled, will be generated.
                                   An octet string expressed as 'sdd.dd Volts' where:
                                   s is the sign ('-' for negative or '+' for positive)
                                   d is a decimal digit or blank space for a leading zero.
                                   The string 'Not Readable!' indicates that the given monitor
                                   is not supported on this system."
                                   
                                   ::= { voltageThresholdsEntry 10 }

       -- 4.3.2.2.x.8
       voltageThresholdEntryWarningResetLowValue OBJECT-TYPE
                                   SYNTAX  OCTET STRING
                                   ACCESS  read-only
                                   STATUS  mandatory
                                   DESCRIPTION
                                   "Voltage threshold reading expressed in Volts(V).
                                   If the voltage drops below this value and
                                   if a warning alert/event had previously been
                                   created, then the alert/event will be reset.
                                   An octet string expressed as 'sdd.dd Volts' where:
                                   s is the sign ('-' for negative or '+' for positive)
                                   d is a decimal digit or blank space for a leading zero.
                                   The string 'Not Readable!' indicates that the given monitor
                                   is not supported on this system."
                                   
                                   ::= { voltageThresholdsEntry 11 }

     -- ********************************************************************************
     -- Vital Product Data(VPD) information
     -- ********************************************************************************
     -- 4.3.5
     vpdInformation  OBJECT IDENTIFIER ::= { monitors 21 }

      -- ********************************************************************************
      -- System Firmware Level VPD
      -- ********************************************************************************
      -- the following has been removed until it is supported
      -- bios vpd was the only section not already commented out
--    systemFirmwareVpd OBJECT IDENTIFIER ::= { vpdInformation 1 }
--
       -- ********************************************************************************
       -- BIOS Firmware Level VPD
       -- ********************************************************************************
       -- 4.3.5.1
--
--     biosVpd OBJECT IDENTIFIER ::= { systemFirmwareVpd 1 }
--
--      biosVpdVersionNumber OBJECT-TYPE
--                    SYNTAX  OCTET STRING
--                    ACCESS  read-only
--                    STATUS  mandatory
--                    DESCRIPTION
--                    "Bios firmware version number (from System BIOS)."
--                    ::= { biosVpd 1 }
--
--      biosVpdBuildLevelName OBJECT-TYPE
--                    SYNTAX  OCTET STRING
--                    ACCESS  read-only
--                    STATUS  mandatory
--                    DESCRIPTION
--                    "Bios firmware build level name (from System BIOS)."
--                    ::= { biosVpd 2 }
--
--      biosVpdBuildDate OBJECT-TYPE
--                    SYNTAX  OCTET STRING
--                    ACCESS  read-only
--                    STATUS  mandatory
--                    DESCRIPTION
--                    "Bios firmware build date (from System BIOS)."
--                    ::= { biosVpd 3 }
--
--
         -- ********************************************************************************
         -- DIAG Firmware Level VPD
         -- ********************************************************************************
         -- 4.3.5.1.1
--       diagVpd OBJECT IDENTIFIER ::= { systemFirmwareVpd 2 }
--
--        diagVpdVersionNumber OBJECT-TYPE
--                      SYNTAX  OCTET STRING
--                      ACCESS  read-only
--                      STATUS  mandatory
--                      DESCRIPTION
--                      "Diagnostics firmware version number (from System BIOS)."
--                      ::= { diagVpd 1 }
--
--        diagVpdBuildLevelName OBJECT-TYPE
--                      SYNTAX  OCTET STRING
--                      ACCESS  read-only
--                      STATUS  mandatory
--                      DESCRIPTION
--                      "Diagnostics firmware build level name (from System BIOS)."
--                      ::= { diagVpd 2 }
--
--        diagVpdBuildDate OBJECT-TYPE
--                      SYNTAX  OCTET STRING
--                      ACCESS  read-only
--                      STATUS  mandatory
--                      DESCRIPTION
--                      "Diagnostics firmware build date (from System BIOS)."
--                      ::= { diagVpd 3 }
--
--
       -- ********************************************************************************
       -- Power backplane firmware VPD
       -- ********************************************************************************
       -- 4.3.5.13.1
--     powerBackplaneFirmwareVpd OBJECT IDENTIFIER ::= { systemFirmwareVpd 15 }
--
       -- 15.1.1
--      powerBackplaneRevisionNumber OBJECT-TYPE
--                    SYNTAX  OCTET STRING
--                    ACCESS  read-only
--                    STATUS  mandatory
--                    DESCRIPTION
--                    "Power Backplane firmware revison number."
--                    ::= { powerBackplaneFirmwareVpd 1 }
--
--
       -- ********************************************************************************
       -- Integrated system management processor VPD
       -- ********************************************************************************
       -- 4.3.5.6??  4.3.5.19 doesn't exist
--     ismpFirmwareVpd OBJECT IDENTIFIER ::= { systemFirmwareVpd 19 }
--
        -- 19.1.1
--      ismpRevisionNumber OBJECT-TYPE
--                    SYNTAX  OCTET STRING
--                    ACCESS  read-only
--                    STATUS  mandatory
--                    DESCRIPTION
--                    "ISMP firmware revison number."
--                    ::= { ismpFirmwareVpd 1 }
--
--
      -- ********************************************************************************
      -- Machine Level VPD
      -- ********************************************************************************
      -- 4.3.5.2.1
      chassisVpd OBJECT IDENTIFIER ::= { vpdInformation 1 }


       bladeCenterVpd OBJECT IDENTIFIER ::= { chassisVpd 1 }

        -- 4.3.5.2.1
        bladeCenterVpdMachineType OBJECT-TYPE
                      SYNTAX  OCTET STRING
                      ACCESS  read-write
                      STATUS  mandatory
                      DESCRIPTION
                      "Machine type VPD information (from System BIOS).  This field must be four 
                      alpha numeric characters."
                      ::= { bladeCenterVpd 1 }

        -- 4.3.5.2.1
        bladeCenterVpdMachineModel OBJECT-TYPE
                      SYNTAX  OCTET STRING
                      ACCESS  read-write
                      STATUS  mandatory
                      DESCRIPTION
                      "Machine model VPD information (from System BIOS).  This field  must be three 
                      alpha numeric characters."
                      ::= { bladeCenterVpd 2 }

        -- 4.3.5.2.1
        bladeCenterSerialNumber OBJECT-TYPE
                      SYNTAX  OCTET STRING
                      ACCESS  read-write
                      STATUS  mandatory
                      DESCRIPTION
                      "Machine serial number VPD information (from System BIOS).  This field must be 
                      seven alpha numeric characters."
                      ::= { bladeCenterVpd 3 }

        -- 4.3.5.2.1
        bladeCenterUUID OBJECT-TYPE
                      SYNTAX  OCTET STRING
                      ACCESS  read-write
                      STATUS  mandatory
                      DESCRIPTION
                      "Machine UUID (Universal Unique ID information) (from System BIOS).  This field 
                      must be 32 alpha numeric characters."
                      ::= { bladeCenterVpd 4 }

        bladeCenterManufacturingId OBJECT-TYPE
                      SYNTAX  OCTET STRING
                      ACCESS  read-only
                      STATUS  mandatory
                      DESCRIPTION
                      "Machine chassis manufacturing ID."
                      ::= { bladeCenterVpd 5 }

        bladeCenterHardwareRevision OBJECT-TYPE
                      SYNTAX  INTEGER
                      ACCESS  read-only
                      STATUS  mandatory
                      DESCRIPTION
                      "Machine chassis hardware revision."
                      ::= { bladeCenterVpd 6 }

        bladeCenterFruNumber OBJECT-TYPE
                      SYNTAX  OCTET STRING
                      ACCESS  read-only
                      STATUS  mandatory
                      DESCRIPTION
                      "Machine chassis FRU number."
                      ::= { bladeCenterVpd 7 }

        bladeCenterManufDate OBJECT-TYPE
                      SYNTAX  OCTET STRING
                      ACCESS  read-only
                      STATUS  mandatory
                      DESCRIPTION
                      "Machine chassis manufature date."
                      ::= { bladeCenterVpd 8 }

        bladeCenterPartNumber OBJECT-TYPE
                      SYNTAX  OCTET STRING
                      ACCESS  read-only
                      STATUS  mandatory
                      DESCRIPTION
                      "Machine chassis part number."
                      ::= { bladeCenterVpd 9 }

        bladeCenterFruSerial OBJECT-TYPE
                      SYNTAX  OCTET STRING
                      ACCESS  read-only
                      STATUS  mandatory
                      DESCRIPTION
                      "Machine chassis FRU serial."
                      ::= { bladeCenterVpd 10 }

      -- ********************************************************************************
      -- Management Module Hardware VPD
      -- ********************************************************************************
      mmHardwareVpd OBJECT IDENTIFIER ::= { vpdInformation 2 }

      mmHardwareVpdTable OBJECT-TYPE
                    SYNTAX  SEQUENCE OF MmHardwareVpdEntry
                    ACCESS  not-accessible
                    STATUS  mandatory
                    DESCRIPTION
                    "Table of the management module hardware components.
                    For consistent results, view as a table and not as
                    individual entries."
                    ::= { mmHardwareVpd 1 }

      mmHardwareVpdEntry OBJECT-TYPE
                    SYNTAX MmHardwareVpdEntry
                    ACCESS  not-accessible
                    STATUS  mandatory
                    DESCRIPTION
                    "Management module hardware VPD entry.
                    For consistent results, view as a table and
                    not as individual entries."
                    INDEX { mmHardwareVpdIndex }
                    ::= { mmHardwareVpdTable 1 }

      MmHardwareVpdEntry ::= SEQUENCE {
                  mmHardwareVpdIndex INTEGER,
                  mmHardwareVpdBayNumber OCTET STRING,
                  mmHardwareVpdManufacturingId OCTET STRING,
                  mmHardwareVpdFruNumber OCTET STRING,
                  mmHardwareVpdHardwareRevision INTEGER,
                  mmHardwareVpdUuid OCTET STRING,
                  mmHardwareVpdManufDate OCTET STRING,
                  mmHardwareVpdPartNumber OCTET STRING,
                  mmHardwareVpdFruSerial OCTET STRING
      }

      mmHardwareVpdIndex  OBJECT-TYPE
                  SYNTAX  INTEGER
                  ACCESS  read-only
                  STATUS  mandatory
                  DESCRIPTION
                  "Management module hardware VPD index.
                  For consistent results, view as a table and
                  not as individual entries."
                  ::= { mmHardwareVpdEntry 1 }

      mmHardwareVpdBayNumber  OBJECT-TYPE
                  SYNTAX  OCTET STRING
                  ACCESS  read-only
                  STATUS  mandatory
                  DESCRIPTION
                  "Management module hardware VPD Bay number.
                  For consistent results, view as a table and
                  not as individual entries."
                  ::= { mmHardwareVpdEntry 2 }

      mmHardwareVpdManufacturingId  OBJECT-TYPE
                  SYNTAX  OCTET STRING
                  ACCESS  read-only
                  STATUS  mandatory
                  DESCRIPTION
                  "Management module hardware VPD manufacturing ID.
                  For consistent results, view as a table and
                  not as individual entries."
                  ::= { mmHardwareVpdEntry 3 }

      mmHardwareVpdFruNumber  OBJECT-TYPE
                  SYNTAX  OCTET STRING
                  ACCESS  read-only
                  STATUS  mandatory
                  DESCRIPTION
                  "Management module hardware VPD FRU number.
                  For consistent results, view as a table and
                  not as individual entries."
                  ::= { mmHardwareVpdEntry 4 }

      mmHardwareVpdHardwareRevision  OBJECT-TYPE
                  SYNTAX  INTEGER
                  ACCESS  read-only
                  STATUS  mandatory
                  DESCRIPTION
                  "Management module hardware VPD hardware revision.
                  For consistent results, view as a table and
                  not as individual entries."
                  ::= { mmHardwareVpdEntry 5 }


      mmHardwareVpdUuid  OBJECT-TYPE
                  SYNTAX  OCTET STRING
                  ACCESS  read-only
                  STATUS  mandatory
                  DESCRIPTION
                  "Management module hardware VPD UUID.
                  For consistent results, view as a table and
                  not as individual entries."
                  ::= { mmHardwareVpdEntry 6 }

      mmHardwareVpdManufDate  OBJECT-TYPE
                  SYNTAX  OCTET STRING
                  ACCESS  read-only
                  STATUS  mandatory
                  DESCRIPTION
                  "Management module hardware VPD manufacture date.
                  For consistent results, view as a table and
                  not as individual entries."
                  ::= { mmHardwareVpdEntry 7 }

      mmHardwareVpdPartNumber  OBJECT-TYPE
                  SYNTAX  OCTET STRING
                  ACCESS  read-only
                  STATUS  mandatory
                  DESCRIPTION
                  "Management module hardware VPD Part number.
                  For consistent results, view as a table and
                  not as individual entries."
                  ::= { mmHardwareVpdEntry 8 }

      mmHardwareVpdFruSerial  OBJECT-TYPE
                  SYNTAX  OCTET STRING
                  ACCESS  read-only
                  STATUS  mandatory
                  DESCRIPTION
                  "Management module hardware VPD FRU serial.
                  For consistent results, view as a table and
                  not as individual entries."
                  ::= { mmHardwareVpdEntry 9 }


      -- ********************************************************************************
      -- System Firmware Level VPD
      -- ********************************************************************************
      mmFirmwareVpd OBJECT IDENTIFIER ::= { vpdInformation 3 }

       -- ********************************************************************************
       -- MM Firmware VPD
       -- ********************************************************************************
       -- 4.3.5.6.1
       mmMainApplVpdTable OBJECT-TYPE
                     SYNTAX  SEQUENCE OF MmMainApplVpdEntry
                     ACCESS  not-accessible
                     STATUS  mandatory
                     DESCRIPTION
                     "Table of MM Firmware VPD."
                     ::= { mmFirmwareVpd 1 }

       mmMainApplVpdEntry OBJECT-TYPE
                     SYNTAX MmMainApplVpdEntry
                     ACCESS  not-accessible
                     STATUS  mandatory
                     DESCRIPTION
                     "MM Firmware VPD entry."
                     INDEX { mmMainApplVpdIndex }
                     ::= { mmMainApplVpdTable 1 }


       MmMainApplVpdEntry ::= SEQUENCE {
                   mmMainApplVpdIndex INTEGER,
                   mmMainApplVpdName OCTET STRING,
                   mmMainApplVpdBuildId OCTET STRING,
                   mmMainApplVpdRevisonNumber OCTET STRING,
                   mmMainApplVpdFilename OCTET STRING,
                   mmMainApplVpdBuildDate OCTET STRING
       }


       mmMainApplVpdIndex  OBJECT-TYPE
                   SYNTAX  INTEGER
                   ACCESS  read-only
                   STATUS  mandatory
                   DESCRIPTION
                   "Firmware VPD index."
                   ::= { mmMainApplVpdEntry 1 }

       mmMainApplVpdName  OBJECT-TYPE
                   SYNTAX  OCTET STRING
                   ACCESS  read-only
                   STATUS  mandatory
                   DESCRIPTION
                   "Firmware VPD name description."
                   ::= { mmMainApplVpdEntry 2 }

       mmMainApplVpdBuildId  OBJECT-TYPE
                   SYNTAX  OCTET STRING
                   ACCESS  read-only
                   STATUS  mandatory
                   DESCRIPTION
                   "Firmware VPD build identification."
                   ::= { mmMainApplVpdEntry 3 }

       mmMainApplVpdRevisonNumber  OBJECT-TYPE
                   SYNTAX  OCTET STRING
                   ACCESS  read-only
                   STATUS  mandatory
                   DESCRIPTION
                   "Firmware VPD revision number."
                   ::= { mmMainApplVpdEntry 4 }

       mmMainApplVpdFilename  OBJECT-TYPE
                   SYNTAX  OCTET STRING
                   ACCESS  read-only
                   STATUS  mandatory
                   DESCRIPTION
                   "Firmware VPD file name."
                   ::= { mmMainApplVpdEntry 5 }

       mmMainApplVpdBuildDate  OBJECT-TYPE
                   SYNTAX  OCTET STRING
                   ACCESS  read-only
                   STATUS  mandatory
                   DESCRIPTION
                   "Firmware VPD build date."
                   ::= { mmMainApplVpdEntry 6 }

       -- ********************************************************************************
       -- MM Firmware VPD
       -- ********************************************************************************
       -- 4.3.5.6.2
       mmBootROMVpdTable OBJECT-TYPE
                     SYNTAX  SEQUENCE OF MmBootROMVpdEntry
                     ACCESS  not-accessible
                     STATUS  mandatory
                     DESCRIPTION
                     "Table of MM Firmware VPD."
                     ::= { mmFirmwareVpd 2 }

       mmBootROMVpdEntry OBJECT-TYPE
                     SYNTAX MmBootROMVpdEntry
                     ACCESS  not-accessible
                     STATUS  mandatory
                     DESCRIPTION
                     "MM Firmware VPD entry."
                     INDEX { mmBootROMVpdIndex }
                     ::= { mmBootROMVpdTable 1 }


       MmBootROMVpdEntry ::= SEQUENCE {
                   mmBootROMVpdIndex INTEGER,
                   mmBootROMVpdName OCTET STRING,
                   mmBootROMVpdBuildId OCTET STRING,
                   mmBootROMVpdRevisonNumber OCTET STRING,
                   mmBootROMVpdFilename OCTET STRING,
                   mmBootROMVpdBuildDate OCTET STRING
       }


       mmBootROMVpdIndex  OBJECT-TYPE
                   SYNTAX  INTEGER
                   ACCESS  read-only
                   STATUS  mandatory
                   DESCRIPTION
                   "Firmware VPD index."
                   ::= { mmBootROMVpdEntry 1 }

       mmBootROMVpdName  OBJECT-TYPE
                   SYNTAX  OCTET STRING
                   ACCESS  read-only
                   STATUS  mandatory
                   DESCRIPTION
                   "Firmware VPD name description."
                   ::= { mmBootROMVpdEntry 2 }

       mmBootROMVpdBuildId  OBJECT-TYPE
                   SYNTAX  OCTET STRING
                   ACCESS  read-only
                   STATUS  mandatory
                   DESCRIPTION
                   "Firmware VPD build identification."
                   ::= { mmBootROMVpdEntry 3 }

       mmBootROMVpdRevisonNumber  OBJECT-TYPE
                   SYNTAX  OCTET STRING
                   ACCESS  read-only
                   STATUS  mandatory
                   DESCRIPTION
                   "Firmware VPD revision number."
                   ::= { mmBootROMVpdEntry 4 }

       mmBootROMVpdFilename  OBJECT-TYPE
                   SYNTAX  OCTET STRING
                   ACCESS  read-only
                   STATUS  mandatory
                   DESCRIPTION
                   "Firmware VPD file name."
                   ::= { mmBootROMVpdEntry 5 }

       mmBootROMVpdBuildDate  OBJECT-TYPE
                   SYNTAX  OCTET STRING
                   ACCESS  read-only
                   STATUS  mandatory
                   DESCRIPTION
                   "Firmware VPD build date."
                   ::= { mmBootROMVpdEntry 6 }


       -- ******************************************************************************** 
       -- MM Firmware VPD
       -- ********************************************************************************
       -- 4.3.5.6.3
       mmRemoteControlVpdTable OBJECT-TYPE
                     SYNTAX  SEQUENCE OF MmRemoteControlVpdEntry
                     ACCESS  not-accessible
                     STATUS  mandatory
                     DESCRIPTION
                     "Table of MM Firmware VPD."
                     ::= { mmFirmwareVpd 3 }

       mmRemoteControlVpdEntry OBJECT-TYPE
                     SYNTAX MmRemoteControlVpdEntry
                     ACCESS  not-accessible
                     STATUS  mandatory
                     DESCRIPTION
                     "MM Firmware VPD entry."
                     INDEX { mmRemoteControlVpdIndex }
                     ::= { mmRemoteControlVpdTable 1 }


       MmRemoteControlVpdEntry ::= SEQUENCE {
                   mmRemoteControlVpdIndex INTEGER,
                   mmRemoteControlVpdName OCTET STRING,
                   mmRemoteControlVpdBuildId OCTET STRING,
                   mmRemoteControlVpdRevisonNumber OCTET STRING,
                   mmRemoteControlVpdFilename OCTET STRING,
                   mmRemoteControlVpdBuildDate OCTET STRING
       }


       mmRemoteControlVpdIndex  OBJECT-TYPE
                   SYNTAX  INTEGER
                   ACCESS  read-only
                   STATUS  mandatory
                   DESCRIPTION
                   "Firmware VPD index."
                   ::= { mmRemoteControlVpdEntry 1 }

       mmRemoteControlVpdName  OBJECT-TYPE
                   SYNTAX  OCTET STRING
                   ACCESS  read-only
                   STATUS  mandatory
                   DESCRIPTION
                   "Firmware VPD name description."
                   ::= { mmRemoteControlVpdEntry 2 }

       mmRemoteControlVpdBuildId  OBJECT-TYPE
                   SYNTAX  OCTET STRING
                   ACCESS  read-only
                   STATUS  mandatory
                   DESCRIPTION
                   "Firmware VPD build identification."
                   ::= { mmRemoteControlVpdEntry 3 }

       mmRemoteControlVpdRevisonNumber  OBJECT-TYPE
                   SYNTAX  OCTET STRING
                   ACCESS  read-only
                   STATUS  mandatory
                   DESCRIPTION
                   "Firmware VPD revision number."
                   ::= { mmRemoteControlVpdEntry 4 }

       mmRemoteControlVpdFilename  OBJECT-TYPE
                   SYNTAX  OCTET STRING
                   ACCESS  read-only
                   STATUS  mandatory
                   DESCRIPTION
                   "Firmware VPD file name."
                   ::= { mmRemoteControlVpdEntry 5 }

       mmRemoteControlVpdBuildDate  OBJECT-TYPE
                   SYNTAX  OCTET STRING
                   ACCESS  read-only
                   STATUS  mandatory
                   DESCRIPTION
                   "Firmware VPD build date."
                   ::= { mmRemoteControlVpdEntry 6 }


       -- ********************************************************************************
       -- MM Firmware VPD
       -- ********************************************************************************
       -- 4.3.5.20.1
       mmPS2toUSBConvVpdTable OBJECT-TYPE
                     SYNTAX  SEQUENCE OF MmPS2toUSBConvVpdEntry
                     ACCESS  not-accessible
                     STATUS  mandatory
                     DESCRIPTION
                     "Table of MM Firmware VPD."
                     ::= { mmFirmwareVpd 4 }

       mmPS2toUSBConvVpdEntry OBJECT-TYPE
                     SYNTAX MmPS2toUSBConvVpdEntry
                     ACCESS  not-accessible
                     STATUS  mandatory
                     DESCRIPTION
                     "MM Firmware VPD entry."
                     INDEX { mmPS2toUSBConvVpdIndex }
                     ::= { mmPS2toUSBConvVpdTable 1 }


       MmPS2toUSBConvVpdEntry ::= SEQUENCE {
                   mmPS2toUSBConvVpdIndex INTEGER,
                   mmPS2toUSBConvVpdName OCTET STRING,
                   mmPS2toUSBConvVpdBuildId OCTET STRING,
                   mmPS2toUSBConvVpdRevisonNumber OCTET STRING,
                   mmPS2toUSBConvVpdFilename OCTET STRING,
                   mmPS2toUSBConvVpdBuildDate OCTET STRING
       }


       mmPS2toUSBConvVpdIndex  OBJECT-TYPE
                   SYNTAX  INTEGER
                   ACCESS  read-only
                   STATUS  mandatory
                   DESCRIPTION
                   "Firmware VPD index."
                   ::= { mmPS2toUSBConvVpdEntry 1 }

       mmPS2toUSBConvVpdName  OBJECT-TYPE
                   SYNTAX  OCTET STRING
                   ACCESS  read-only
                   STATUS  mandatory
                   DESCRIPTION
                   "Firmware VPD name description."
                   ::= { mmPS2toUSBConvVpdEntry 2 }

       mmPS2toUSBConvVpdBuildId  OBJECT-TYPE
                   SYNTAX  OCTET STRING
                   ACCESS  read-only
                   STATUS  mandatory
                   DESCRIPTION
                   "Firmware VPD build identification."
                   ::= { mmPS2toUSBConvVpdEntry 3 }

       mmPS2toUSBConvVpdRevisonNumber  OBJECT-TYPE
                   SYNTAX  OCTET STRING
                   ACCESS  read-only
                   STATUS  mandatory
                   DESCRIPTION
                   "Firmware VPD revision number."
                   ::= { mmPS2toUSBConvVpdEntry 4 }

       mmPS2toUSBConvVpdFilename  OBJECT-TYPE
                   SYNTAX  OCTET STRING
                   ACCESS  read-only
                   STATUS  mandatory
                   DESCRIPTION
                   "Firmware VPD file name."
                   ::= { mmPS2toUSBConvVpdEntry 5 }

       mmPS2toUSBConvVpdBuildDate  OBJECT-TYPE
                   SYNTAX  OCTET STRING
                   ACCESS  read-only
                   STATUS  mandatory
                   DESCRIPTION
                   "Firmware VPD build date."
                   ::= { mmPS2toUSBConvVpdEntry 6 }


       -- ********************************************************************************
       -- MM Firmware VPD
       -- ********************************************************************************
       -- 4.3.5.20.2
       mmToUSBIntfVpdTable OBJECT-TYPE
                     SYNTAX  SEQUENCE OF MmToUSBIntfVpdEntry
                     ACCESS  not-accessible
                     STATUS  mandatory
                     DESCRIPTION
                     "Table of MM Firmware VPD."
                     ::= { mmFirmwareVpd 5 }

       mmToUSBIntfVpdEntry OBJECT-TYPE
                     SYNTAX MmToUSBIntfVpdEntry
                     ACCESS  not-accessible
                     STATUS  mandatory
                     DESCRIPTION
                     "MM Firmware VPD entry."
                     INDEX { mmToUSBIntfVpdIndex }
                     ::= { mmToUSBIntfVpdTable 1 }


       MmToUSBIntfVpdEntry ::= SEQUENCE {
                   mmToUSBIntfVpdIndex INTEGER,
                   mmToUSBIntfVpdName OCTET STRING,
                   mmToUSBIntfVpdBuildId OCTET STRING,
                   mmToUSBIntfVpdRevisonNumber OCTET STRING,
                   mmToUSBIntfVpdFilename OCTET STRING,
                   mmToUSBIntfVpdBuildDate OCTET STRING
       }


       mmToUSBIntfVpdIndex  OBJECT-TYPE
                   SYNTAX  INTEGER
                   ACCESS  read-only
                   STATUS  mandatory
                   DESCRIPTION
                   "Firmware VPD index."
                   ::= { mmToUSBIntfVpdEntry 1 }

       mmToUSBIntfVpdName  OBJECT-TYPE
                   SYNTAX  OCTET STRING
                   ACCESS  read-only
                   STATUS  mandatory
                   DESCRIPTION
                   "Firmware VPD name description."
                   ::= { mmToUSBIntfVpdEntry 2 }

       mmToUSBIntfVpdBuildId  OBJECT-TYPE
                   SYNTAX  OCTET STRING
                   ACCESS  read-only
                   STATUS  mandatory
                   DESCRIPTION
                   "Firmware VPD build identification."
                   ::= { mmToUSBIntfVpdEntry 3 }

       mmToUSBIntfVpdRevisonNumber  OBJECT-TYPE
                   SYNTAX  OCTET STRING
                   ACCESS  read-only
                   STATUS  mandatory
                   DESCRIPTION
                   "Firmware VPD revision number."
                   ::= { mmToUSBIntfVpdEntry 4 }

       mmToUSBIntfVpdFilename  OBJECT-TYPE
                   SYNTAX  OCTET STRING
                   ACCESS  read-only
                   STATUS  mandatory
                   DESCRIPTION
                   "Firmware VPD file name."
                   ::= { mmToUSBIntfVpdEntry 5 }

       mmToUSBIntfVpdBuildDate  OBJECT-TYPE
                   SYNTAX  OCTET STRING
                   ACCESS  read-only
                   STATUS  mandatory
                   DESCRIPTION
                   "Firmware VPD build date."
                   ::= { mmToUSBIntfVpdEntry 6 }


      -- ********************************************************************************
      -- Inventory Management VPD
      -- ********************************************************************************
      -- 4.3.5.21
      inventoryManagementVpdTable OBJECT-TYPE
                    SYNTAX  SEQUENCE OF InventoryManagementVpdEntry
                    ACCESS  not-accessible
                    STATUS  mandatory
                    DESCRIPTION
                    "Table of the hardware components, (modules or blades)
                    for which the system provides VPD information.
                    For consistent results, view as a table and not as
                    individual entries."
                    ::= { vpdInformation 21 }

      inventoryManagementVpdEntry OBJECT-TYPE
                    SYNTAX InventoryManagementVpdEntry
                    ACCESS  not-accessible
                    STATUS  mandatory
                    DESCRIPTION
                    "System component hardware VPD entry.
                    For consistent results, view as a table and
                    not as individual entries."
                    INDEX { componentLevelVpdIndex }
                    ::= { inventoryManagementVpdTable 1 }

      InventoryManagementVpdEntry ::= SEQUENCE {
                  componentLevelVpdIndex INTEGER,
                  componentLevelVpdFruNumber OCTET STRING,
                  componentLevelVpdSerialNumber OCTET STRING,
                  componentLevelVpdManufacturingId OCTET STRING,
                  componentLevelVpdBayNumber OCTET STRING,
                  componentLevelVpdTypeCode INTEGER,
                  componentLevelVpdMachineType OCTET STRING,
                  componentLevelVpdHardwareRevision INTEGER
      }

      componentLevelVpdIndex  OBJECT-TYPE
                  SYNTAX  INTEGER
                  ACCESS  read-only
                  STATUS  mandatory
                  DESCRIPTION
                  "System component level VPD index.
                  For consistent results, view as a table and
                  not as individual entries."
                  ::= { inventoryManagementVpdEntry 1 }

      componentLevelVpdFruNumber  OBJECT-TYPE
                  SYNTAX  OCTET STRING
                  ACCESS  read-only
                  STATUS  mandatory
                  DESCRIPTION
                  "System component level VPD FRU number.
                  For consistent results, view as a table and
                  not as individual entries."
                  ::= { inventoryManagementVpdEntry 2 }

      componentLevelVpdSerialNumber  OBJECT-TYPE
                  SYNTAX  OCTET STRING
                  ACCESS  read-only
                  STATUS  mandatory
                  DESCRIPTION
                  "System component level VPD serial number.
                  For consistent results, view as a table and
                  not as individual entries."
                  ::= { inventoryManagementVpdEntry 3 }

      componentLevelVpdManufacturingId  OBJECT-TYPE
                  SYNTAX  OCTET STRING
                  ACCESS  read-only
                  STATUS  mandatory
                  DESCRIPTION
                  "System component level VPD manufacturing ID.
                  For consistent results, view as a table and
                  not as individual entries."
                  ::= { inventoryManagementVpdEntry 4 }

      componentLevelVpdBayNumber  OBJECT-TYPE
                  SYNTAX  OCTET STRING
                  ACCESS  read-only
                  STATUS  mandatory
                  DESCRIPTION
                  "System component level VPD Bay number.
                  For consistent results, view as a table and
                  not as individual entries."
                  ::= { inventoryManagementVpdEntry 5 }

      componentLevelVpdTypeCode  OBJECT-TYPE
                  SYNTAX  INTEGER  {
                    unknown(0),
                    bladeX86OneWay(1),
                    bladeX86TwoWay(2),
                    bladeX86FourWay(4),
                    switchModuleEthernet(17),
                    switchModuleFiberChannel(18),
                    scalabilityPortModule(19),
                    switchModuleInfiniband(20),
                    switchModuleMixedProtocol(21),
                    switchModuleCopperPassThrough(40),
                    bladeEthernetDaughterCard(33),
                    bladeFiberChannelDaughterCard(34),
                    bladeStorageExpansionUnit(35),
                    serialPortExpansionCard(47),
                    bladeGenericExpansionCard(49),
                    managementModule(81),
                    chassis(97),
                    powerModule(113),
                    mediaTray(129)
                  }
                  ACCESS  read-only
                  STATUS  mandatory
                  DESCRIPTION
                  "System component level VPD Type Code.
                  Describes what the blade or module is.
                  For consistent results, view as a table and
                  not as individual entries."
                  ::= { inventoryManagementVpdEntry 6 }

      componentLevelVpdMachineType  OBJECT-TYPE
                  SYNTAX  OCTET STRING
                  ACCESS  read-only
                  STATUS  mandatory
                  DESCRIPTION
                  "System component level VPD machine type.
                  For consistent results, view as a table and
                  not as individual entries."
                  ::= { inventoryManagementVpdEntry 7 }

      componentLevelVpdHardwareRevision  OBJECT-TYPE
                  SYNTAX  INTEGER
                  ACCESS  read-only
                  STATUS  mandatory
                  DESCRIPTION
                  "System component level VPD hardware revision.
                  For consistent results, view as a table and
                  not as individual entries."
                  ::= { inventoryManagementVpdEntry 8 }

      -- ********************************************************************************
      -- System Component Level VPD Activity log
      -- ********************************************************************************
      -- 4.3.5.22
      inventoryManagementActivityVpdTable OBJECT-TYPE
                    SYNTAX  SEQUENCE OF InventoryManagementActivityVpdEntry
                    ACCESS  not-accessible
                    STATUS  mandatory
                    DESCRIPTION
                    "Table of system component hardware VPD activity log.
                    For consistent results, view as a table and not as individual entries."
                    ::= { vpdInformation 22 }

      inventoryManagementActivityVpdEntry OBJECT-TYPE
                    SYNTAX InventoryManagementActivityVpdEntry
                    ACCESS  not-accessible
                    STATUS  mandatory
                    DESCRIPTION
                    "System component hardware VPD activity log entry.
                    For consistent results, view as a table and not as individual entries."
                    INDEX { componentLevelActivityVpdIndex }
                    ::= { inventoryManagementActivityVpdTable 1 }

      InventoryManagementActivityVpdEntry ::= SEQUENCE {
                  componentLevelActivityVpdIndex INTEGER,
                  componentLevelActivityVpdFruNumber OCTET STRING,
                  componentLevelActivityVpdSerialNumber OCTET STRING,
                  componentLevelActivityVpdManufacturingId OCTET STRING,
                  componentLevelActivityVpdBayNumber OCTET STRING,
--                  componentLevelActivityVpdTypeCode INTEGER,
--                  componentLevelActivityVpdMachineType OCTET STRING,
--                  componentLevelActivityVpdHardwareRevision INTEGER,
                  componentLevelActivityVpdAction OCTET STRING,
                  componentLevelActivityVpdTimestamp OCTET STRING

      }

      componentLevelActivityVpdIndex  OBJECT-TYPE
                  SYNTAX  INTEGER
                  ACCESS  read-only
                  STATUS  mandatory
                  DESCRIPTION
                  "System component level VPD activity log index.
                  For consistent results, view as a table and
                  not as individual entries."
                  ::= { inventoryManagementActivityVpdEntry 1 }

      componentLevelActivityVpdFruNumber  OBJECT-TYPE
                  SYNTAX  OCTET STRING
                  ACCESS  read-only
                  STATUS  mandatory
                  DESCRIPTION
                  "System component level VPD activity log FRU number.
                  For consistent results, view as a table and not as individual entries."
                  ::= { inventoryManagementActivityVpdEntry 2 }

      componentLevelActivityVpdSerialNumber  OBJECT-TYPE
                  SYNTAX  OCTET STRING
                  ACCESS  read-only
                  STATUS  mandatory
                  DESCRIPTION
                  "System component level VPD activity log serial number.
                  For consistent results, view as a table and not as individual entries."
                  ::= { inventoryManagementActivityVpdEntry 3 }

      componentLevelActivityVpdManufacturingId  OBJECT-TYPE
                  SYNTAX  OCTET STRING
                  ACCESS  read-only
                  STATUS  mandatory
                  DESCRIPTION
                  "System component level VPD activity log manufacturing ID.
                  For consistent results, view as a table and not as individual entries."
                  ::= { inventoryManagementActivityVpdEntry 4 }

      componentLevelActivityVpdBayNumber  OBJECT-TYPE
                  SYNTAX  OCTET STRING
                  ACCESS  read-only
                  STATUS  mandatory
                  DESCRIPTION
                  "System component level VPD activity log Bay number.
                  For consistent results, view as a table and not as individual entries."
                  ::= { inventoryManagementActivityVpdEntry 5 }

--      componentLevelActivityVpdTypeCode  OBJECT-TYPE
--                  SYNTAX  INTEGER  {
--                    unknown(0),
--                    bladeX86OneWay(1),
--                    bladeX86TwoWay(2),
--                    bladeX86FourWay(4),
--                    switchModuleEthernet(17),
--                    switchModuleFiberChannel(18),
--                    scalabilityPortModule(19),
--                    switchModuleInfiniband(20),
--                    switchModuleMixedProtocol(21),
--                    bladeEthernetDaughterCard(33),
--                    bladeFiberChannelDaughterCard(34),
--                    bladeStorageExpansionUnit(35),
--                    serialPortExpansionCard(47),
--                    managementModule(81),
--                    chassis(97),
--                    powerModule(113),
--                    mediaTray(129)
--                  }
--                  ACCESS  read-only
--                  STATUS  mandatory
--                  DESCRIPTION
--                  "System component level VPD Type Code.
--                  Describes what the blade or module is.
--                  For consistent results, view as a table and
--                  not as individual entries."
--                  ::= { inventoryManagementActivityVpdEntry 6 }

--      componentLevelActivityVpdMachineType  OBJECT-TYPE
--                  SYNTAX  OCTET STRING
--                  ACCESS  read-only
--                  STATUS  mandatory
--                  DESCRIPTION
--                  "System component level VPD machine type.
--                  For consistent results, view as a table and
--                  not as individual entries."
--                  ::= { inventoryManagementActivityVpdEntry 7 }

--      componentLevelActivityVpdHardwareRevision  OBJECT-TYPE
--                  SYNTAX  INTEGER
--                  ACCESS  read-only
--                  STATUS  mandatory
--                  DESCRIPTION
--                  "System component level VPD activity hardware revision.
--                  For consistent results, view as a table and
--                  not as individual entries."
--                  ::= { inventoryManagementActivityVpdEntry 8 }

      componentLevelActivityVpdAction  OBJECT-TYPE
                  SYNTAX  OCTET STRING
                  ACCESS  read-only
                  STATUS  mandatory
                  DESCRIPTION
                  "System component level VPD activity log action (added/removed).
                  For consistent results, view as a table and not as individual entries."
                  ::= {inventoryManagementActivityVpdEntry 9 }

      componentLevelActivityVpdTimestamp  OBJECT-TYPE
                  SYNTAX  OCTET STRING
                  ACCESS  read-only
                  STATUS  mandatory
                  DESCRIPTION
                  "System component level VPD activity log timestamp.
                  For consistent results, view as a table and not as individual entries."
                  ::= { inventoryManagementActivityVpdEntry 10 }

      -- ********************************************************************************
      -- Blade Hardware VPD
      -- ********************************************************************************
      bladeHardwareVpd OBJECT IDENTIFIER ::= { vpdInformation 4 }

      bladeHardwareVpdTable OBJECT-TYPE
                    SYNTAX  SEQUENCE OF BladeHardwareVpdEntry
                    ACCESS  not-accessible
                    STATUS  mandatory
                    DESCRIPTION
                    "Table of VPD information for the blade server
                    hardware components.
                    For consistent results, view as a table and not as
                    individual entries."
                    ::= { bladeHardwareVpd 1 }

      bladeHardwareVpdEntry OBJECT-TYPE
                    SYNTAX BladeHardwareVpdEntry
                    ACCESS  not-accessible
                    STATUS  mandatory
                    DESCRIPTION
                    "Blade server hardware VPD entry.
                    For consistent results, view as a table and
                    not as individual entries."
                    INDEX { bladeHardwareVpdIndex }
                    ::= { bladeHardwareVpdTable 1 }

      BladeHardwareVpdEntry ::= SEQUENCE {
                  bladeHardwareVpdIndex INTEGER,
                  bladeHardwareVpdBayNumber OCTET STRING,
                  bladeHardwareVpdManufacturingId OCTET STRING,
                  bladeHardwareVpdFruNumber OCTET STRING,
                  bladeHardwareVpdHardwareRevision INTEGER,
                  bladeHardwareVpdSerialNumber OCTET STRING,
                  bladeHardwareVpdMachineType OCTET STRING,
                  bladeHardwareVpdUuid OCTET STRING,
                  bladeHardwareVpdManufDate OCTET STRING,
                  bladeHardwareVpdPartNumber OCTET STRING,
                  bladeHardwareVpdFruSerial OCTET STRING,
                  bladeHardwareVpdMachineModel OCTET STRING,
                  bladeDaughterVpdCardType INTEGER,
                  bladeDaughterVpdManufacturingId OCTET STRING,
                  bladeDaughterVpdFruNumber OCTET STRING,
                  bladeDaughterVpdHardwareRevision INTEGER,
                  bladeDaughterVpdSerialNumber OCTET STRING,
                  bladeDaughterVpdMachineType OCTET STRING,
                  bladeDaughterVpdUuid OCTET STRING,
                  bladeDaughterVpdManufDate OCTET STRING,
                  bladeDaughterVpdPartNumber OCTET STRING,
                  bladeDaughterVpdFruSerial OCTET STRING
      }

      bladeHardwareVpdIndex  OBJECT-TYPE
                  SYNTAX  INTEGER
                  ACCESS  read-only
                  STATUS  mandatory
                  DESCRIPTION
                  "Blade hardware VPD index.
                  For consistent results, view as a table and
                  not as individual entries."
                  ::= { bladeHardwareVpdEntry 1 }

      bladeHardwareVpdBayNumber  OBJECT-TYPE
                  SYNTAX  OCTET STRING
                  ACCESS  read-only
                  STATUS  mandatory
                  DESCRIPTION
                  "Blade hardware VPD Bay number.
                  For consistent results, view as a table and
                  not as individual entries."
                  ::= { bladeHardwareVpdEntry 2 }

      bladeHardwareVpdManufacturingId  OBJECT-TYPE
                  SYNTAX  OCTET STRING
                  ACCESS  read-only
                  STATUS  mandatory
                  DESCRIPTION
                  "Blade hardware VPD manufacturing ID.
                  For consistent results, view as a table and
                  not as individual entries."
                  ::= { bladeHardwareVpdEntry 3 }

      bladeHardwareVpdFruNumber  OBJECT-TYPE
                  SYNTAX  OCTET STRING
                  ACCESS  read-only
                  STATUS  mandatory
                  DESCRIPTION
                  "Blade hardware VPD FRU number.
                  For consistent results, view as a table and
                  not as individual entries."
                  ::= { bladeHardwareVpdEntry 4 }

      bladeHardwareVpdHardwareRevision  OBJECT-TYPE
                  SYNTAX  INTEGER
                  ACCESS  read-only
                  STATUS  mandatory
                  DESCRIPTION
                  "Blade hardware VPD hardware revision.
                  For consistent results, view as a table and
                  not as individual entries."
                  ::= { bladeHardwareVpdEntry 5 }

      bladeHardwareVpdSerialNumber  OBJECT-TYPE
                  SYNTAX  OCTET STRING
                  ACCESS  read-only
                  STATUS  mandatory
                  DESCRIPTION
                  "Blade hardware VPD serial number.
                  For consistent results, view as a table and
                  not as individual entries."
                  ::= { bladeHardwareVpdEntry 6 }

      bladeHardwareVpdMachineType  OBJECT-TYPE
                  SYNTAX  OCTET STRING
                  ACCESS  read-only
                  STATUS  mandatory
                  DESCRIPTION
                  "Blade hardware VPD machine type.
                  For consistent results, view as a table and
                  not as individual entries."
                  ::= { bladeHardwareVpdEntry 7 }

      bladeHardwareVpdUuid  OBJECT-TYPE
                  SYNTAX  OCTET STRING
                  ACCESS  read-only
                  STATUS  mandatory
                  DESCRIPTION
                  "Blade hardware VPD UUID.
                  For consistent results, view as a table and
                  not as individual entries."
                  ::= { bladeHardwareVpdEntry 8 }

      bladeHardwareVpdManufDate  OBJECT-TYPE
                  SYNTAX  OCTET STRING
                  ACCESS  read-only
                  STATUS  mandatory
                  DESCRIPTION
                  "Blade hardware VPD Manufature Date.
                  For consistent results, view as a table and
                  not as individual entries."
                  ::= { bladeHardwareVpdEntry 9 }

      bladeHardwareVpdPartNumber  OBJECT-TYPE
                  SYNTAX  OCTET STRING
                  ACCESS  read-only
                  STATUS  mandatory
                  DESCRIPTION
                  "Blade hardware VPD Part number.
                  For consistent results, view as a table and
                  not as individual entries."
                  ::= { bladeHardwareVpdEntry 10 }

      bladeHardwareVpdFruSerial  OBJECT-TYPE
                  SYNTAX  OCTET STRING
                  ACCESS  read-only
                  STATUS  mandatory
                  DESCRIPTION
                  "Blade hardware VPD FRU serial.
                  For consistent results, view as a table and
                  not as individual entries."
                  ::= { bladeHardwareVpdEntry 11 }

       bladeHardwareVpdMachineModel  OBJECT-TYPE
                  SYNTAX  OCTET STRING
                  ACCESS  read-only
                  STATUS  mandatory
                  DESCRIPTION
                  "Blade hardware VPD machine model.
                  For consistent results, view as a table and
                  not as individual entries."
                  ::= { bladeHardwareVpdEntry 12 }
      bladeDaughterVpdCardType  OBJECT-TYPE
                  SYNTAX  INTEGER  {
                    unknown(0),
                    networkExpansion(1),
                    storageExpansion(2),
                    pciExpansion(3),
                    genericExpansion(4)
                  }
                  ACCESS  read-only
                  STATUS  mandatory
                  DESCRIPTION
                  "Blade daughter card VPD Type Code.
                  Describes what the blade or module is.
                  For consistent results, view as a table and
                  not as individual entries."
                  ::= { bladeHardwareVpdEntry 20 }

      bladeDaughterVpdManufacturingId  OBJECT-TYPE
                  SYNTAX  OCTET STRING
                  ACCESS  read-only
                  STATUS  mandatory
                  DESCRIPTION
                  "Blade daughter card VPD manufacturing ID.
                  For consistent results, view as a table and
                  not as individual entries."
                  ::= { bladeHardwareVpdEntry 21 }

      bladeDaughterVpdFruNumber  OBJECT-TYPE
                  SYNTAX  OCTET STRING
                  ACCESS  read-only
                  STATUS  mandatory
                  DESCRIPTION
                  "Blade daughter card VPD FRU number.
                  For consistent results, view as a table and
                  not as individual entries."
                  ::= { bladeHardwareVpdEntry 22 }

      bladeDaughterVpdHardwareRevision  OBJECT-TYPE
                  SYNTAX  INTEGER
                  ACCESS  read-only
                  STATUS  mandatory
                  DESCRIPTION
                  "Blade daughter card VPD hardware revision.
                  For consistent results, view as a table and
                  not as individual entries."
                  ::= { bladeHardwareVpdEntry 23 }

      bladeDaughterVpdSerialNumber  OBJECT-TYPE
                  SYNTAX  OCTET STRING
                  ACCESS  read-only
                  STATUS  mandatory
                  DESCRIPTION
                  "Blade daughter card VPD Serial number.
                  For consistent results, view as a table and
                  not as individual entries."
                  ::= { bladeHardwareVpdEntry 24 }

      bladeDaughterVpdMachineType  OBJECT-TYPE
                  SYNTAX  OCTET STRING
                  ACCESS  read-only
                  STATUS  mandatory
                  DESCRIPTION
                  "Blade daughter card VPD Machine type.
                  For consistent results, view as a table and
                  not as individual entries."
                  ::= { bladeHardwareVpdEntry 25 }

      bladeDaughterVpdUuid  OBJECT-TYPE
                  SYNTAX  OCTET STRING
                  ACCESS  read-only
                  STATUS  mandatory
                  DESCRIPTION
                  "Blade daughter VPD UUID.
                  For consistent results, view as a table and
                  not as individual entries."
                  ::= { bladeHardwareVpdEntry 26 }

      bladeDaughterVpdManufDate  OBJECT-TYPE
                  SYNTAX  OCTET STRING
                  ACCESS  read-only
                  STATUS  mandatory
                  DESCRIPTION
                  "Blade daughter VPD Manufacture date.
                  For consistent results, view as a table and
                  not as individual entries."
                  ::= { bladeHardwareVpdEntry 27 }

      bladeDaughterVpdPartNumber  OBJECT-TYPE
                  SYNTAX  OCTET STRING
                  ACCESS  read-only
                  STATUS  mandatory
                  DESCRIPTION
                  "Blade daughter VPD Part number.
                  For consistent results, view as a table and
                  not as individual entries."
                  ::= { bladeHardwareVpdEntry 28 }

      bladeDaughterVpdFruSerial  OBJECT-TYPE
                  SYNTAX  OCTET STRING
                  ACCESS  read-only
                  STATUS  mandatory
                  DESCRIPTION
                  "Blade daughter VPD FRU Serial.
                  For consistent results, view as a table and
                  not as individual entries."
                  ::= { bladeHardwareVpdEntry 29 }


      -- ********************************************************************************
      -- Blade MAC Address VPD
      -- ********************************************************************************

      bladeMACAddressVpdTable OBJECT-TYPE
                    SYNTAX  SEQUENCE OF BladeMACAddressVpdEntry
                    ACCESS  not-accessible
                    STATUS  mandatory
                    DESCRIPTION
                    "Table of MAC addresses of the blade server and its daughter cards.
                    For consistent results, view as a table and not as individual entries."
                    ::= { bladeHardwareVpd 2 }

      bladeMACAddressVpdEntry OBJECT-TYPE
                    SYNTAX BladeMACAddressVpdEntry
                    ACCESS  not-accessible
                    STATUS  mandatory
                    DESCRIPTION
                    "Blade server MAC address entry.  For consistent results, view as a 
                    table and not as individual entries."
                    INDEX { bladeMACAddressVpdIndex }
                    ::= { bladeMACAddressVpdTable 1 }


      BladeMACAddressVpdEntry ::= SEQUENCE {
                  bladeMACAddressVpdIndex INTEGER,
                  bladeMACAddress1Vpd              OCTET STRING,
                  bladeMACAddress2Vpd              OCTET STRING,
                  bladeMACAddress3Vpd              OCTET STRING,
                  bladeMACAddress4Vpd              OCTET STRING,
                  bladeDaughterCard1MACAddress1Vpd OCTET STRING,
                  bladeDaughterCard1MACAddress2Vpd OCTET STRING,
                  bladeDaughterCard1MACAddress3Vpd OCTET STRING,
                  bladeDaughterCard1MACAddress4Vpd OCTET STRING,
                  bladeDaughterCard2MACAddress1Vpd OCTET STRING,
                  bladeDaughterCard2MACAddress2Vpd OCTET STRING,
                  bladeDaughterCard2MACAddress3Vpd OCTET STRING,
                  bladeDaughterCard2MACAddress4Vpd OCTET STRING
      }

      bladeMACAddressVpdIndex  OBJECT-TYPE
                  SYNTAX  INTEGER
                  ACCESS  read-only
                  STATUS  mandatory
                  DESCRIPTION
                  "Blade server index.  For consistent results, view as a table and
                  not as individual entries."
                  ::= { bladeMACAddressVpdEntry 1 }

      bladeMACAddress1Vpd  OBJECT-TYPE
                  SYNTAX  OCTET STRING
                  ACCESS  read-only
                  STATUS  mandatory
                  DESCRIPTION
                  "Blade server MAC address 1.  For consistent results, view as a table and
                  not as individual entries."
                  ::= { bladeMACAddressVpdEntry 2 }

      bladeMACAddress2Vpd  OBJECT-TYPE
                  SYNTAX  OCTET STRING
                  ACCESS  read-only
                  STATUS  mandatory
                  DESCRIPTION
                  "Blade server MAC address 2.  For consistent results, view as a table and
                  not as individual entries."
                  ::= { bladeMACAddressVpdEntry 3 }

      bladeMACAddress3Vpd  OBJECT-TYPE
                  SYNTAX  OCTET STRING
                  ACCESS  read-only
                  STATUS  mandatory
                  DESCRIPTION
                  "Blade server MAC address 3.  For consistent results, view as a table and
                  not as individual entries."
                  ::= { bladeMACAddressVpdEntry 4 }

      bladeMACAddress4Vpd  OBJECT-TYPE
                  SYNTAX  OCTET STRING
                  ACCESS  read-only
                  STATUS  mandatory
                  DESCRIPTION
                  "Blade server MAC address 4.  For consistent results, view as a table and
                  not as individual entries."
                  ::= { bladeMACAddressVpdEntry 5 }

      bladeDaughterCard1MACAddress1Vpd  OBJECT-TYPE
                  SYNTAX  OCTET STRING
                  ACCESS  read-only
                  STATUS  mandatory
                  DESCRIPTION
                  "Blade server Daughter Card 1 MAC address 1.  For consistent results, view 
                  as a table and not as individual entries."
                  ::= { bladeMACAddressVpdEntry 10 }

      bladeDaughterCard1MACAddress2Vpd  OBJECT-TYPE
                  SYNTAX  OCTET STRING
                  ACCESS  read-only
                  STATUS  mandatory
                  DESCRIPTION
                  "Blade server Daughter Card 1 MAC address 2.  For consistent results, view 
                  as a table and not as individual entries."
                  ::= { bladeMACAddressVpdEntry 11 }

      bladeDaughterCard1MACAddress3Vpd  OBJECT-TYPE
                  SYNTAX  OCTET STRING
                  ACCESS  read-only
                  STATUS  mandatory
                  DESCRIPTION
                  "Blade server daughter card 1 MAC address 3.  For consistent results, view 
                  as a table and not as individual entries."
                  ::= { bladeMACAddressVpdEntry 12 }

      bladeDaughterCard1MACAddress4Vpd  OBJECT-TYPE
                  SYNTAX  OCTET STRING
                  ACCESS  read-only
                  STATUS  mandatory
                  DESCRIPTION
                  "Blade server daughter card 1 MAC address 4.  For consistent results, view 
                  as a table and not as individual entries."
                  ::= { bladeMACAddressVpdEntry 13 }

      bladeDaughterCard2MACAddress1Vpd  OBJECT-TYPE
                  SYNTAX  OCTET STRING
                  ACCESS  read-only
                  STATUS  mandatory
                  DESCRIPTION
                  "Blade server daughter card 2 MAC address 1.  For consistent results, view 
                  as a table and not as individual entries."
                  ::= { bladeMACAddressVpdEntry 18 }

      bladeDaughterCard2MACAddress2Vpd  OBJECT-TYPE
                  SYNTAX  OCTET STRING
                  ACCESS  read-only
                  STATUS  mandatory
                  DESCRIPTION
                  "Blade server daughter card 2 MAC address 2.  For consistent results, view 
                  as a table and not as individual entries."
                  ::= { bladeMACAddressVpdEntry 19 }

      bladeDaughterCard2MACAddress3Vpd  OBJECT-TYPE
                  SYNTAX  OCTET STRING
                  ACCESS  read-only
                  STATUS  mandatory
                  DESCRIPTION
                  "Blade server daughter card 2 MAC address 3.  For consistent results, view 
                  as a table and not as individual entries."
                  ::= { bladeMACAddressVpdEntry 20 }

      bladeDaughterCard2MACAddress4Vpd  OBJECT-TYPE
                  SYNTAX  OCTET STRING
                  ACCESS  read-only
                  STATUS  mandatory
                  DESCRIPTION
                  "Blade server daughter card 2 MAC address 4.  For consistent results, view 
                  as a table and not as individual entries."
                  ::= { bladeMACAddressVpdEntry 21 }

         
      -- ********************************************************************************
      -- System Firmware Level VPD
      -- ********************************************************************************
      bladeFirmwareVpd OBJECT IDENTIFIER ::= { vpdInformation 5 }


       bladeBiosVPDTable OBJECT-TYPE
                      SYNTAX  SEQUENCE OF BladeBiosVPDEntry
                      ACCESS  not-accessible
                      STATUS  mandatory
                      DESCRIPTION
                      "Table of blade firmware vital product data (VPD) information."
                      ::= { bladeFirmwareVpd 1 }

        bladeBiosVPDEntry OBJECT-TYPE
                      SYNTAX BladeBiosVPDEntry
                      ACCESS  not-accessible
                      STATUS  mandatory
                      DESCRIPTION
                      "Blade firmware VPD table entry"
                      INDEX { bladeBiosVpdIndex }
                      ::= { bladeBiosVPDTable 1 }


        BladeBiosVPDEntry ::= SEQUENCE {
                    bladeBiosVpdIndex INTEGER,
                    bladeBiosVpdId INTEGER,
                    bladeBiosVpdExists INTEGER,
                    bladeBiosVpdPowerState INTEGER,
                    bladeBiosVpdName OCTET STRING,
                    bladeBiosVpdBuildId OCTET STRING,
                    bladeBiosVpdRevision OCTET STRING,
                    bladeBiosVpdDate OCTET STRING
        }

        bladeBiosVpdIndex  OBJECT-TYPE
                    SYNTAX  INTEGER
                    ACCESS  read-only
                    STATUS  mandatory
                    DESCRIPTION
                    "Blade firmware VPD table index."
                    ::= { bladeBiosVPDEntry 1 }


        bladeBiosVpdId  OBJECT-TYPE
                    SYNTAX  INTEGER {
--                       managementModule(0),
                      blade1(1),
                      blade2(2),
                      blade3(3),
                      blade4(4),
                      blade5(5),
                      blade6(6),
                      blade7(7),
                      blade8(8),
                      blade9(9),
                      blade10(10),
                      blade11(11),
                      blade12(12),
                      blade13(13),
                      blade14(14)
                    }
                    ACCESS  read-only
                    STATUS  mandatory
                    DESCRIPTION
                    "The numeric blade ID."
                    ::= { bladeBiosVPDEntry 2 }

        bladeBiosVpdExists OBJECT-TYPE
                    SYNTAX  INTEGER {
                      false(0),
                      true(1)
                    }
                    ACCESS  read-only
                    STATUS  mandatory
                    DESCRIPTION
                    "Indicates whether the server blade specified exists or not."
                    ::= { bladeBiosVPDEntry 3 }

        bladeBiosVpdPowerState OBJECT-TYPE
                    SYNTAX  INTEGER {
                      off(0),
                      on(1)
                    }
                    ACCESS  read-only
                    STATUS  mandatory
                    DESCRIPTION
                    "Indicates whether the server blade specified is powered on or not."
                    ::= { bladeBiosVPDEntry 4 }

        bladeBiosVpdName OBJECT-TYPE
                    SYNTAX  OCTET STRING
                    ACCESS  read-only
                    STATUS  mandatory
                    DESCRIPTION
                    "The name of the blade as a null terminated string."
                    ::= { bladeBiosVPDEntry 5 }

        bladeBiosVpdBuildId OBJECT-TYPE
                    SYNTAX  OCTET STRING
                    ACCESS  read-only
                    STATUS  mandatory
                    DESCRIPTION
                    "The build ID for the blade firmware."
                    ::= { bladeBiosVPDEntry 6 }

        bladeBiosVpdRevision OBJECT-TYPE
                    SYNTAX  OCTET STRING
                    ACCESS  read-only
                    STATUS  mandatory
                    DESCRIPTION
                    "The revision of the blade firmware."
                    ::= { bladeBiosVPDEntry 7 }

        bladeBiosVpdDate OBJECT-TYPE
                    SYNTAX  OCTET STRING
                    ACCESS  read-only
                    STATUS  mandatory
                    DESCRIPTION
                    "The date of the blade firmware."
                    ::= { bladeBiosVPDEntry 8 }



       bladeDiagsVPDTable OBJECT-TYPE
                      SYNTAX  SEQUENCE OF BladeDiagsVPDEntry
                      ACCESS  not-accessible
                      STATUS  mandatory
                      DESCRIPTION
                      "Table of blade firmware vital product data (VPD) information."
                      ::= { bladeFirmwareVpd 2 }

        bladeDiagsVPDEntry OBJECT-TYPE
                      SYNTAX BladeDiagsVPDEntry
                      ACCESS  not-accessible
                      STATUS  mandatory
                      DESCRIPTION
                      "Blade firmware VPD table entry"
                      INDEX { bladeDiagsVpdIndex }
                      ::= { bladeDiagsVPDTable 1 }


        BladeDiagsVPDEntry ::= SEQUENCE {
                    bladeDiagsVpdIndex INTEGER,
                    bladeDiagsVpdId INTEGER,
                    bladeDiagsVpdExists INTEGER,
                    bladeDiagsVpdPowerState INTEGER,
                    bladeDiagsVpdName OCTET STRING,
                    bladeDiagsVpdBuildId OCTET STRING,
                    bladeDiagsVpdRevision OCTET STRING,
                    bladeDiagsVpdDate OCTET STRING
        }

        bladeDiagsVpdIndex  OBJECT-TYPE
                    SYNTAX  INTEGER
                    ACCESS  read-only
                    STATUS  mandatory
                    DESCRIPTION
                    "Blade firmware VPD table index."
                    ::= { bladeDiagsVPDEntry 1 }


        bladeDiagsVpdId  OBJECT-TYPE
                    SYNTAX  INTEGER {
--                       managementModule(0),
                      blade1(1),
                      blade2(2),
                      blade3(3),
                      blade4(4),
                      blade5(5),
                      blade6(6),
                      blade7(7),
                      blade8(8),
                      blade9(9),
                      blade10(10),
                      blade11(11),
                      blade12(12),
                      blade13(13),
                      blade14(14)
                    }
                    ACCESS  read-only
                    STATUS  mandatory
                    DESCRIPTION
                    "The numeric blade ID."
                    ::= { bladeDiagsVPDEntry 2 }

        bladeDiagsVpdExists OBJECT-TYPE
                    SYNTAX  INTEGER {
                      false(0),
                      true(1)
                    }
                    ACCESS  read-only
                    STATUS  mandatory
                    DESCRIPTION
                    "Indicates whether the server blade specified exists or not."
                    ::= { bladeDiagsVPDEntry 3 }

        bladeDiagsVpdPowerState OBJECT-TYPE
                    SYNTAX  INTEGER {
                      off(0),
                      on(1)
                    }
                    ACCESS  read-only
                    STATUS  mandatory
                    DESCRIPTION
                    "Indicates whether the server blade specified is powered on or not."
                    ::= { bladeDiagsVPDEntry 4 }

        bladeDiagsVpdName OBJECT-TYPE
                    SYNTAX  OCTET STRING
                    ACCESS  read-only
                    STATUS  mandatory
                    DESCRIPTION
                    "The name of the blade as a null terminated string."
                    ::= { bladeDiagsVPDEntry 5 }

        bladeDiagsVpdBuildId OBJECT-TYPE
                    SYNTAX  OCTET STRING
                    ACCESS  read-only
                    STATUS  mandatory
                    DESCRIPTION
                    "The build ID for the blade firmware."
                    ::= { bladeDiagsVPDEntry 6 }

        bladeDiagsVpdRevision OBJECT-TYPE
                    SYNTAX  OCTET STRING
                    ACCESS  read-only
                    STATUS  mandatory
                    DESCRIPTION
                    "The revision of the blade firmware."
                    ::= { bladeDiagsVPDEntry 7 }

        bladeDiagsVpdDate OBJECT-TYPE
                    SYNTAX  OCTET STRING
                    ACCESS  read-only
                    STATUS  mandatory
                    DESCRIPTION
                    "The date of the blade firmware."
                    ::= { bladeDiagsVPDEntry 8 }




       bladeSysMgmtProcVPDTable OBJECT-TYPE
                      SYNTAX  SEQUENCE OF BladeSysMgmtProcVPDEntry
                      ACCESS  not-accessible
                      STATUS  mandatory
                      DESCRIPTION
                      "Table of blade firmware vital product data (VPD) information."
                      ::= { bladeFirmwareVpd 3 }

        bladeSysMgmtProcVPDEntry OBJECT-TYPE
                      SYNTAX BladeSysMgmtProcVPDEntry
                      ACCESS  not-accessible
                      STATUS  mandatory
                      DESCRIPTION
                      "Blade firmware VPD table entry"
                      INDEX { bladeSysMgmtProcVpdIndex }
                      ::= { bladeSysMgmtProcVPDTable 1 }


        BladeSysMgmtProcVPDEntry ::= SEQUENCE {
                    bladeSysMgmtProcVpdIndex INTEGER,
                    bladeSysMgmtProcVpdId INTEGER,
                    bladeSysMgmtProcVpdExists INTEGER,
                    bladeSysMgmtProcVpdPowerState INTEGER,
                    bladeSysMgmtProcVpdName OCTET STRING,
                    bladeSysMgmtProcVpdBuildId OCTET STRING,
                    bladeSysMgmtProcVpdRevision OCTET STRING
        }

        bladeSysMgmtProcVpdIndex  OBJECT-TYPE
                    SYNTAX  INTEGER
                    ACCESS  read-only
                    STATUS  mandatory
                    DESCRIPTION
                    "Blade firmware VPD table index."
                    ::= { bladeSysMgmtProcVPDEntry 1 }


        bladeSysMgmtProcVpdId  OBJECT-TYPE
                    SYNTAX  INTEGER {
--                       managementModule(0),
                      blade1(1),
                      blade2(2),
                      blade3(3),
                      blade4(4),
                      blade5(5),
                      blade6(6),
                      blade7(7),
                      blade8(8),
                      blade9(9),
                      blade10(10),
                      blade11(11),
                      blade12(12),
                      blade13(13),
                      blade14(14)
                    }
                    ACCESS  read-only
                    STATUS  mandatory
                    DESCRIPTION
                    "The numeric blade ID."
                    ::= { bladeSysMgmtProcVPDEntry 2 }

        bladeSysMgmtProcVpdExists OBJECT-TYPE
                    SYNTAX  INTEGER {
                      false(0),
                      true(1)
                    }
                    ACCESS  read-only
                    STATUS  mandatory
                    DESCRIPTION
                    "Indicates whether the server blade specified exists or not."
                    ::= { bladeSysMgmtProcVPDEntry 3 }

        bladeSysMgmtProcVpdPowerState OBJECT-TYPE
                    SYNTAX  INTEGER {
                      off(0),
                      on(1)
                    }
                    ACCESS  read-only
                    STATUS  mandatory
                    DESCRIPTION
                    "Indicates whether the server blade specified is powered on or not."
                    ::= { bladeSysMgmtProcVPDEntry 4 }

        bladeSysMgmtProcVpdName OBJECT-TYPE
                    SYNTAX  OCTET STRING
                    ACCESS  read-only
                    STATUS  mandatory
                    DESCRIPTION
                    "The name of the blade as a null terminated string."
                    ::= { bladeSysMgmtProcVPDEntry 5 }

        bladeSysMgmtProcVpdBuildId OBJECT-TYPE
                    SYNTAX  OCTET STRING
                    ACCESS  read-only
                    STATUS  mandatory
                    DESCRIPTION
                    "The build ID for the blade firmware."
                    ::= { bladeSysMgmtProcVPDEntry 6 }

        bladeSysMgmtProcVpdRevision OBJECT-TYPE
                    SYNTAX  OCTET STRING
                    ACCESS  read-only
                    STATUS  mandatory
                    DESCRIPTION
                    "The revision of the blade firmware."
                    ::= { bladeSysMgmtProcVPDEntry 7 }


      -- ********************************************************************************
      -- Switch Module Hardware VPD
      -- ********************************************************************************
      smHardwareVpd OBJECT IDENTIFIER ::= { vpdInformation 6 }

      smHardwareVpdTable OBJECT-TYPE
                    SYNTAX  SEQUENCE OF SmHardwareVpdEntry
                    ACCESS  not-accessible
                    STATUS  mandatory
                    DESCRIPTION
                    "Table of the switch module hardware components.
                    For consistent results, view as a table and not as
                    individual entries."
                    ::= { smHardwareVpd 1 }

      smHardwareVpdEntry OBJECT-TYPE
                    SYNTAX SmHardwareVpdEntry
                    ACCESS  not-accessible
                    STATUS  mandatory
                    DESCRIPTION
                    "Switch module hardware VPD entry.
                    For consistent results, view as a table and
                    not as individual entries."
                    INDEX { smHardwareVpdIndex }
                    ::= { smHardwareVpdTable 1 }

      SmHardwareVpdEntry ::= SEQUENCE {
                  smHardwareVpdIndex INTEGER,
                  smHardwareVpdBayNumber OCTET STRING,
                  smHardwareVpdManufacturingId OCTET STRING,
                  smHardwareVpdFruNumber OCTET STRING,
                  smHardwareVpdHardwareRevision INTEGER,
                  smHardwareVpdUuid OCTET STRING,
                  smHardwareVpdManufDate OCTET STRING,
                  smHardwareVpdPartNumber OCTET STRING,
                  smHardwareVpdFruSerial OCTET STRING
      }

      smHardwareVpdIndex  OBJECT-TYPE
                  SYNTAX  INTEGER
                  ACCESS  read-only
                  STATUS  mandatory
                  DESCRIPTION
                  "Switch module hardware VPD index.
                  For consistent results, view as a table and
                  not as individual entries."
                  ::= { smHardwareVpdEntry 1 }

      smHardwareVpdBayNumber  OBJECT-TYPE
                  SYNTAX  OCTET STRING
                  ACCESS  read-only
                  STATUS  mandatory
                  DESCRIPTION
                  "Switch module hardware VPD Bay number.
                  For consistent results, view as a table and
                  not as individual entries."
                  ::= { smHardwareVpdEntry 2 }

      smHardwareVpdManufacturingId  OBJECT-TYPE
                  SYNTAX  OCTET STRING
                  ACCESS  read-only
                  STATUS  mandatory
                  DESCRIPTION
                  "Switch module hardware VPD manufacturing ID.
                  For consistent results, view as a table and
                  not as individual entries."
                  ::= { smHardwareVpdEntry 3 }

      smHardwareVpdFruNumber  OBJECT-TYPE
                  SYNTAX  OCTET STRING
                  ACCESS  read-only
                  STATUS  mandatory
                  DESCRIPTION
                  "Switch module hardware VPD FRU number.
                  For consistent results, view as a table and
                  not as individual entries."
                  ::= { smHardwareVpdEntry 4 }

      smHardwareVpdHardwareRevision  OBJECT-TYPE
                  SYNTAX  INTEGER
                  ACCESS  read-only
                  STATUS  mandatory
                  DESCRIPTION
                  "Switch module hardware VPD hardware revision.
                  For consistent results, view as a table and
                  not as individual entries."
                  ::= { smHardwareVpdEntry 5 }

      smHardwareVpdUuid  OBJECT-TYPE
                  SYNTAX  OCTET STRING
                  ACCESS  read-only
                  STATUS  mandatory
                  DESCRIPTION
                  "Switch module hardware VPD UUID.
                  For consistent results, view as a table and
                  not as individual entries."
                  ::= { smHardwareVpdEntry 8 }

      smHardwareVpdManufDate  OBJECT-TYPE
                  SYNTAX  OCTET STRING
                  ACCESS  read-only
                  STATUS  mandatory
                  DESCRIPTION
                  "Switch module hardware VPD manufacture Date.
                  For consistent results, view as a table and
                  not as individual entries."
                  ::= { smHardwareVpdEntry 9 }

      smHardwareVpdPartNumber  OBJECT-TYPE
                  SYNTAX  OCTET STRING
                  ACCESS  read-only
                  STATUS  mandatory
                  DESCRIPTION
                  "Switch module hardware VPD Part Number.
                  For consistent results, view as a table and
                  not as individual entries."
                  ::= { smHardwareVpdEntry 10 }

      smHardwareVpdFruSerial  OBJECT-TYPE
                  SYNTAX  OCTET STRING
                  ACCESS  read-only
                  STATUS  mandatory
                  DESCRIPTION
                  "Switch module hardware VPD FRU Serial.
                  For consistent results, view as a table and
                  not as individual entries."
                  ::= { smHardwareVpdEntry 11 }



       -- ********************************************************************************
       -- Switch module Information
       -- ********************************************************************************

       -- 22.3.3
       smFirmwareVpd OBJECT IDENTIFIER ::= { vpdInformation 7 }
        -- Server blade switch module information

        -- 22.3.3.1
         smMainAppVpdTable OBJECT-TYPE
                     SYNTAX  SEQUENCE OF SmMainAppVpdEntry
                     ACCESS  not-accessible
                     STATUS  mandatory
                     DESCRIPTION
                     "Switch module main application VPD information table."
                     ::= {smFirmwareVpd 1}

          smMainAppVpdEntry  OBJECT-TYPE
                        SYNTAX SmMainAppVpdEntry
                        ACCESS  not-accessible
                        STATUS  mandatory
                        DESCRIPTION
                        "Switch module main application VPD table entry"
                        INDEX { smMainAppVpdIndex }
                        ::= { smMainAppVpdTable 1 }

          SmMainAppVpdEntry ::= SEQUENCE {
                      smMainAppVpdIndex INTEGER,
                      smMainAppVpdId INTEGER,
                      smMainAppVpdExists INTEGER,
                      smMainAppVpdSwitchType INTEGER,
                      smMainApp1VpdRevisionNumber OCTET STRING,
                      smMainApp1VpdBuildId OCTET STRING,
                      smMainApp1VpdBuildDate OCTET STRING,
                      smMainApp2VpdRevisionNumber OCTET STRING,
                      smMainApp2VpdBuildId OCTET STRING,
                      smMainApp2VpdBuildDate OCTET STRING
          }

          smMainAppVpdIndex OBJECT-TYPE
                      SYNTAX  INTEGER
                      ACCESS  read-only
                      STATUS  mandatory
                      DESCRIPTION
                      "Switch module main application VPD entry index."
                      ::= { smMainAppVpdEntry 1 }

          smMainAppVpdId OBJECT-TYPE
                      SYNTAX  INTEGER {
                        module1(1),
                        module2(2),
                        module3(3),
                        module4(4)
                      }
                      ACCESS  read-only
                      STATUS  mandatory
                      DESCRIPTION
                      "The switch module numeric identifier."
                      ::= { smMainAppVpdEntry 2 }

          smMainAppVpdExists OBJECT-TYPE
                      SYNTAX  INTEGER {
                        false(0),
                        true(1)
                      }
                      ACCESS  read-only
                      STATUS  mandatory
                      DESCRIPTION
                      "Indicates whether the switch module specified exists or not."
                      ::= { smMainAppVpdEntry 3 }

          smMainAppVpdSwitchType OBJECT-TYPE
                      SYNTAX  INTEGER {
                        unknown(0),
                        ethernet(1),
                        fibre(2),
                        opm(3),
                        serialCM(4),
                        copperPassThrough(5),
                        infiniband(6)
                      }
                      ACCESS  read-only
                      STATUS  mandatory
                      DESCRIPTION
                      "Indicates the type of switch module installed."
                      ::= { smMainAppVpdEntry 4 }

          smMainApp1VpdBuildId OBJECT-TYPE
                        SYNTAX  OCTET STRING
                        ACCESS  read-only
                        STATUS  mandatory
                        DESCRIPTION
                        "Switch module firmware build id."
                        ::= { smMainAppVpdEntry 5 }

          smMainApp1VpdBuildDate OBJECT-TYPE
                        SYNTAX  OCTET STRING
                        ACCESS  read-only
                        STATUS  mandatory
                        DESCRIPTION
                        "Switch module firmware build date."
                        ::= { smMainAppVpdEntry 6 }

          smMainApp1VpdRevisionNumber OBJECT-TYPE
                        SYNTAX  OCTET STRING
                        ACCESS  read-only
                        STATUS  mandatory
                        DESCRIPTION
                        "Switch module firmware revision number."
                        ::= { smMainAppVpdEntry 7 }
          
          smMainApp2VpdBuildId OBJECT-TYPE
                        SYNTAX  OCTET STRING
                        ACCESS  read-only
                        STATUS  mandatory
                        DESCRIPTION
                        "Switch module firmware build id."
                        ::= { smMainAppVpdEntry 8 }

          smMainApp2VpdBuildDate OBJECT-TYPE
                        SYNTAX  OCTET STRING
                        ACCESS  read-only
                        STATUS  mandatory
                        DESCRIPTION
                        "Switch module firmware build date."
                        ::= { smMainAppVpdEntry 9 }

          smMainApp2VpdRevisionNumber OBJECT-TYPE
                        SYNTAX  OCTET STRING
                        ACCESS  read-only
                        STATUS  mandatory
                        DESCRIPTION
                        "Switch module firmware revision number."
                        ::= { smMainAppVpdEntry 10 }





         smBootRomVpdTable OBJECT-TYPE
                     SYNTAX  SEQUENCE OF SmBootRomVpdEntry
                     ACCESS  not-accessible
                     STATUS  mandatory
                     DESCRIPTION
                     "Switch module boot ROM VPD information table."
                     ::= {smFirmwareVpd 2}

          smBootRomVpdEntry  OBJECT-TYPE
                        SYNTAX SmBootRomVpdEntry
                        ACCESS  not-accessible
                        STATUS  mandatory
                        DESCRIPTION
                        "Switch module boot ROM VPD table entry"
                        INDEX { smBootRomVpdIndex }
                        ::= { smBootRomVpdTable 1 }

          SmBootRomVpdEntry ::= SEQUENCE {
                      smBootRomVpdIndex INTEGER,
                      smBootRomVpdId INTEGER,
                      smBootRomVpdExists INTEGER,
                      smBootRomVpdSwitchType INTEGER,
                      smBootRomVpdRevisionNumber OCTET STRING,
                      smBootRomVpdBuildId OCTET STRING,
                      smBootRomVpdBuildDate OCTET STRING
          }

          smBootRomVpdIndex OBJECT-TYPE
                      SYNTAX  INTEGER
                      ACCESS  read-only
                      STATUS  mandatory
                      DESCRIPTION
                      "Switch module boot ROM VPD entry index."
                      ::= { smBootRomVpdEntry 1 }

          smBootRomVpdId OBJECT-TYPE
                      SYNTAX  INTEGER {
                        module1(1),
                        module2(2),
                        module3(3),
                        module4(4)
                      }
                      ACCESS  read-only
                      STATUS  mandatory
                      DESCRIPTION
                      "The switch module numeric identifier."
                      ::= { smBootRomVpdEntry 2 }

          smBootRomVpdExists OBJECT-TYPE
                      SYNTAX  INTEGER {
                        false(0),
                        true(1)
                      }
                      ACCESS  read-only
                      STATUS  mandatory
                      DESCRIPTION
                      "Indicates whether the switch module specified exists or not."
                      ::= { smBootRomVpdEntry 3 }

          smBootRomVpdSwitchType OBJECT-TYPE
                      SYNTAX  INTEGER {
                        unknown(0),
                        ethernet(1),
                        fibre(2),
                        opm(3),
                        serialCM(4), 
                        copperPassThrough(5),
                        infiniband(6)
                      }
                      ACCESS  read-only
                      STATUS  mandatory
                      DESCRIPTION
                      "Indicates the type of switch module installed."
                      ::= { smBootRomVpdEntry 4 }

          smBootRomVpdBuildId OBJECT-TYPE
                        SYNTAX  OCTET STRING
                        ACCESS  read-only
                        STATUS  mandatory
                        DESCRIPTION
                        "Switch module firmware build ID."
                        ::= { smBootRomVpdEntry 5 }

          smBootRomVpdBuildDate OBJECT-TYPE
                        SYNTAX  OCTET STRING
                        ACCESS  read-only
                        STATUS  mandatory
                        DESCRIPTION
                        "Switch module firmware build date."
                        ::= { smBootRomVpdEntry 6 }

          smBootRomVpdRevisionNumber OBJECT-TYPE
                        SYNTAX  OCTET STRING
                        ACCESS  read-only
                        STATUS  mandatory
                        DESCRIPTION
                        "Switch module firmware revision number."
                        ::= { smBootRomVpdEntry 7 }


      -- ********************************************************************************
      -- Power Module Hardware VPD
      -- ********************************************************************************
      pmHardwareVpd OBJECT IDENTIFIER ::= { vpdInformation 8 }

      pmHardwareVpdTable OBJECT-TYPE
                    SYNTAX  SEQUENCE OF PmHardwareVpdEntry
                    ACCESS  not-accessible
                    STATUS  mandatory
                    DESCRIPTION
                    "Table of the power module hardware components.
                    For consistent results, view as a table and not as
                    individual entries."
                    ::= { pmHardwareVpd 1 }

      pmHardwareVpdEntry OBJECT-TYPE
                    SYNTAX PmHardwareVpdEntry
                    ACCESS  not-accessible
                    STATUS  mandatory
                    DESCRIPTION
                    "Power module hardware VPD entry.
                    For consistent results, view as a table and
                    not as individual entries."
                    INDEX { pmHardwareVpdIndex }
                    ::= { pmHardwareVpdTable 1 }

      PmHardwareVpdEntry ::= SEQUENCE {
                  pmHardwareVpdIndex INTEGER,
                  pmHardwareVpdBayNumber OCTET STRING,
                  pmHardwareVpdManufacturingId OCTET STRING,
                  pmHardwareVpdFruNumber OCTET STRING,
                  pmHardwareVpdHardwareRevision INTEGER,
                  pmHardwareVpdUuid OCTET STRING,
                  pmHardwareVpdManufDate OCTET STRING,
                  pmHardwareVpdPartNumber OCTET STRING,
                  pmHardwareVpdFruSerial OCTET STRING
      }

      pmHardwareVpdIndex  OBJECT-TYPE
                  SYNTAX  INTEGER
                  ACCESS  read-only
                  STATUS  mandatory
                  DESCRIPTION
                  "Power module hardware VPD index.
                  For consistent results, view as a table and
                  not as individual entries."
                  ::= { pmHardwareVpdEntry 1 }

      pmHardwareVpdBayNumber  OBJECT-TYPE
                  SYNTAX  OCTET STRING
                  ACCESS  read-only
                  STATUS  mandatory
                  DESCRIPTION
                  "Power module hardware VPD Bay number.
                  For consistent results, view as a table and
                  not as individual entries."
                  ::= { pmHardwareVpdEntry 2 }

      pmHardwareVpdManufacturingId  OBJECT-TYPE
                  SYNTAX  OCTET STRING
                  ACCESS  read-only
                  STATUS  mandatory
                  DESCRIPTION
                  "Power module hardware VPD manufacturing ID.
                  For consistent results, view as a table and
                  not as individual entries."
                  ::= { pmHardwareVpdEntry 3 }

      pmHardwareVpdFruNumber  OBJECT-TYPE
                  SYNTAX  OCTET STRING
                  ACCESS  read-only
                  STATUS  mandatory
                  DESCRIPTION
                  "Power module hardware VPD FRU number.
                  For consistent results, view as a table and
                  not as individual entries."
                  ::= { pmHardwareVpdEntry 4 }

      pmHardwareVpdHardwareRevision  OBJECT-TYPE
                  SYNTAX  INTEGER
                  ACCESS  read-only
                  STATUS  mandatory
                  DESCRIPTION
                  "Power module hardware VPD hardware revision.
                  For consistent results, view as a table and
                  not as individual entries."
                  ::= { pmHardwareVpdEntry 5 }

      pmHardwareVpdUuid  OBJECT-TYPE
                  SYNTAX  OCTET STRING
                  ACCESS  read-only
                  STATUS  mandatory
                  DESCRIPTION
                  "Power module hardware VPD UUID.
                  For consistent results, view as a table and
                  not as individual entries."
                  ::= { pmHardwareVpdEntry 8 }

      pmHardwareVpdManufDate  OBJECT-TYPE
                  SYNTAX  OCTET STRING
                  ACCESS  read-only
                  STATUS  mandatory
                  DESCRIPTION
                  "Power module hardware VPD Manufacture Date.
                  For consistent results, view as a table and
                  not as individual entries."
                  ::= { pmHardwareVpdEntry 9 }

      pmHardwareVpdPartNumber  OBJECT-TYPE
                  SYNTAX  OCTET STRING
                  ACCESS  read-only
                  STATUS  mandatory
                  DESCRIPTION
                  "Power module hardware VPD PartNumber.
                  For consistent results, view as a table and
                  not as individual entries."
                  ::= { pmHardwareVpdEntry 10 }

      pmHardwareVpdFruSerial  OBJECT-TYPE
                  SYNTAX  OCTET STRING
                  ACCESS  read-only
                  STATUS  mandatory
                  DESCRIPTION
                  "Power module hardware VPD FRU Serial.
                  For consistent results, view as a table and
                  not as individual entries."
                  ::= { pmHardwareVpdEntry 11 }


      -- ********************************************************************************
      -- Media Tray Hardware VPD
      -- ********************************************************************************
      mtHardwareVpd OBJECT IDENTIFIER ::= { vpdInformation 9 }

      mtHardwareVpdManufacturingId  OBJECT-TYPE
                  SYNTAX  OCTET STRING
                  ACCESS  read-only
                  STATUS  mandatory
                  DESCRIPTION
                  "Media tray hardware VPD manufacturing ID.
                  For consistent results, view as a table and
                  not as individual entries."
                  ::= { mtHardwareVpd 3 }

      mtHardwareVpdFruNumber  OBJECT-TYPE
                  SYNTAX  OCTET STRING
                  ACCESS  read-only
                  STATUS  mandatory
                  DESCRIPTION
                  "Media tray hardware VPD FRU number.
                  For consistent results, view as a table and
                  not as individual entries."
                  ::= { mtHardwareVpd 4 }

      mtHardwareVpdHardwareRevision  OBJECT-TYPE
                  SYNTAX  INTEGER
                  ACCESS  read-only
                  STATUS  mandatory
                  DESCRIPTION
                  "Media tray hardware VPD hardware revision.
                  For consistent results, view as a table and
                  not as individual entries."
                  ::= { mtHardwareVpd 5 }

      mtHardwareVpdUuid  OBJECT-TYPE
                  SYNTAX  OCTET STRING
                  ACCESS  read-only
                  STATUS  mandatory
                  DESCRIPTION
                  "Media tray hardware VPD UUID.
                  For consistent results, view as a table and
                  not as individual entries."
                  ::= { mtHardwareVpd 8 }



      -- ********************************************************************************
      -- MM Clock
      -- ********************************************************************************
      -- 4.4
      spClock        OBJECT IDENTIFIER ::= { configureSP 4 }

       -- 4.4.1
       spClockDateAndTimeSetting OBJECT-TYPE
                    SYNTAX  OCTET STRING
                    ACCESS  read-write
                    STATUS  mandatory
                    DESCRIPTION
                    "MM clock date and time setting.
                    A date-time specification for the local time of day.
                    For example to set the date and time to
                    March 4, 2001 at 06:00:00AM, set the value to:'03/04/2001,06:00:00'.
                    field  contents         range
                    _____  ________         _____
                      1     month           01..12
                      2     separator       '/'
                      3     day             01..31
                      4     separator       '/'
                      5     year            2000..2089
                      6     separator       ','
                      7     hour            00..23
                      8     separator       ':'
                      9     minutes         00..59
                      10    separator       ':'
                      11    seconds         00..59
                    "
                    ::= { spClock  1 }

       -- 4.4.2
       spClockTimezoneSetting OBJECT-TYPE
                    SYNTAX  OCTET STRING
                    ACCESS  read-write
                    STATUS  mandatory
                    DESCRIPTION
                    "MM clock Greenwich Mean Time(GMT) offset and Daylight Saving Time(DST)
                    settings.

                    The following table lists GMT offsets and associated DST
                    information.  DST is not observed in time zones where
                    the 'Observe DST' value does not contain 'yes' in the table.
                    Also, note that in some cases additional information
                    is required to determine the clock adjustment when DST is
                    observed.  The additional information is required when the
                    GMT offset being written is +2:00 or +10:00.

                    Examples
                          -to set the GMT offset to +3:30,
                           set the value to:'+3:30,no'

                          -for Eastern Standard Time and observing DST,
                           set the value to:'-5:00,yes'

                          -for Egypt and observing DST,
                           set the value to:'+2:00,yes,6'


                     GMT    Observe  Additional
                    Offset    DST?    DST value
                    ______  _______  __________
                     +0:00  yes|no
                     +1:00  yes|no
                     +2:00  yes|no   When 'Observe DST?' value is 'yes':
                                     5 (for E.Europe)
                                     4 (for GTB)
                                     6 (for Egypt)
                                     7 (for FLE)
                     +3:00  yes|no
                     +3:30  yes|no
                     +4:00  no
                     +4:30  no
                     +5:00  yes|no
                     +5:30  no
                     +6:00  no
                     +7:00  no
                     +8:00  no
                     +9:00  yes|no
                     +9:30  yes|no
                    +10:00  yes|no   When 'Observe DST?' value is 'yes':
                                     9  (for AUS Eastern)
                                     10 (for Tasmania)
                                     4  (for Vladivostok)
                    +11:00  no
                    +12:00  yes|no
                    -12:00  no
                    -11:00  no
                    -10:00  no
                     -9:00  yes|no
                     -8:00  yes|no
                     -7:00  yes|no
                     -6:00  yes|no
                     -5:00  yes|no
                     -4:00  yes|no
                     -3:30  yes|no
                     -3:00  yes|no
                     -2:00  yes|no
                     -1:00  yes|no
                     "
                    ::= { spClock  2 }


      -- ********************************************************************************
      -- MM identification
      -- ********************************************************************************
      -- 4.5
      spIdentification        OBJECT IDENTIFIER ::= { configureSP 5 }

       -- 4.5.1
       spTxtId      OBJECT-TYPE
                    SYNTAX  OCTET STRING (SIZE(0..16))
                    ACCESS  read-write
                    STATUS  mandatory
                    DESCRIPTION
                    "MM text ID.  Note:  Do not put any 'space
                    characters' at end of the ID. Only alphanumeric 
                    characters, underscores,hyphens, pound signs, 
                    and periods are allowed."
                    ::= { spIdentification 1 }

      -- ********************************************************************************
      -- Network Configuration
      -- ********************************************************************************
      -- 4.9
      networkConfiguration  OBJECT IDENTIFIER ::= { configureSP 9 }

       -- ********************************************************************************
       -- Network Interfaces
       -- ********************************************************************************
       -- 4.9.1
       networkInterfaces  OBJECT IDENTIFIER ::= { networkConfiguration 1 }
        -- ********************************************************************************
        -- Ethernet Interface 1
        -- ********************************************************************************
        -- 4.9.1.1
        extEthernetInterface  OBJECT IDENTIFIER ::= { networkInterfaces 1 }

         -- 4.9.1.1.1
         extEthernetInterfaceType OBJECT-TYPE
                      SYNTAX  OCTET STRING (SIZE(0..16))
                      ACCESS  read-only
                      STATUS  mandatory
                      DESCRIPTION
                      "The type of interface.  Indicates 'Ethernet-1'."
                      ::= { extEthernetInterface 1 }

         -- 4.9.1.1.3
         extEthernetInterfaceHostName  OBJECT-TYPE
                      SYNTAX  OCTET STRING (SIZE(0..64))
                      ACCESS  read-write
                      STATUS  mandatory
                      DESCRIPTION
                      "Contains the 64 byte null terminated DNS host name for this
                      interface."
                      ::= { extEthernetInterface 3 }

         -- 4.9.1.1.4
         extEthernetInterfaceIPAddress   OBJECT-TYPE
                      SYNTAX  IpAddress
                      ACCESS  read-write
                      STATUS  mandatory
                      DESCRIPTION
                      "Contains the IP address for the ethernet interface."
                      ::= { extEthernetInterface 4 }

         -- 4.9.1.1.5
         extEthernetInterfaceDataRate   OBJECT-TYPE
                      SYNTAX  INTEGER {
                        enet10Megabit(3),
                        enet100Megabit(4),
                        autoSpeed(5)
                      }
                      ACCESS  read-write
                      STATUS  mandatory
                      DESCRIPTION
                      "Specifies the data transfer rate to be used over the ethernet
                      interface:  10Mb, 100Mb, or Auto."
                      ::= { extEthernetInterface 5 }

         -- 4.9.1.1.6
         extEthernetInterfaceDuplexSetting  OBJECT-TYPE
                      SYNTAX  INTEGER {
                        fullDuplex(1),
                        halfDuplex(2),
                        autoDuplex(3)
                      }
                      ACCESS  read-write
                      STATUS  mandatory
                      DESCRIPTION
                      "Specifies the duplex settings for the data transfer rate to be used over
                      the ethernet interface:  Half, Full, or Auto."
                      ::= { extEthernetInterface 6 }

         -- 4.9.1.1.7
         extEthernetInterfaceLAA OBJECT-TYPE
                      SYNTAX  OCTET STRING (SIZE(17))
                      ACCESS  read-write
                      STATUS  mandatory
                      DESCRIPTION
                      "Specifies the locally administered MAC address.  The locally administered
                      address must be a hexadecimal value between 000000000000 - FFFFFFFFFFFF.  This
                      value must be in the form XX:XX:XX:XX:XX:XX where 'X' is a number between 0 - 9 and
                      A - F.  This MM subsystem does not allow use of a multicast address.  A multicast
                      address has the least significant bit of the first byte set to a 1.  The first
                      byte must, therefore, be an even number."
                      ::= { extEthernetInterface 7 }

         -- 4.9.1.1.8
         extEthernetInterfaceDhcpEnabled  OBJECT-TYPE
                      SYNTAX  INTEGER {
                        dhcpDisabled(0),
                        dhcpEnabled(1),
                        tryDhcpThenTryStatic(2)
                      }
                      ACCESS  read-write
                      STATUS  mandatory
                      DESCRIPTION
                      "Disable or enable DHCP on this interface."
                      ::= { extEthernetInterface 8 }

         -- 4.9.1.1.9
         extEthernetInterfaceGatewayIPAddress   OBJECT-TYPE
                      SYNTAX  IpAddress
                      ACCESS  read-write
                      STATUS  mandatory
                      DESCRIPTION
                      "Contains the IP address of the gateway/router for the ethernet
                       interface."
                      ::= { extEthernetInterface 9 }

         -- 4.9.1.1.10
         extEthernetInterfaceBIA OBJECT-TYPE
                      SYNTAX  OCTET STRING (SIZE(17))
                      ACCESS  read-only
                      STATUS  mandatory
                      DESCRIPTION
                      "Specifies the burned-in MAC (BIA) address."
                      ::= { extEthernetInterface 10 }

         -- 4.9.1.1.13
         extEthernetInterfaceMTU   OBJECT-TYPE
                      SYNTAX  INTEGER
                      ACCESS  read-write
                      STATUS  mandatory
                      DESCRIPTION
                      "Contains the Maximum Transmission Unit(MTU) for the ethernet
                      interface"
                      ::= { extEthernetInterface 13 }

         -- 4.9.1.1.14
         extEthernetInterfaceSubnetMask   OBJECT-TYPE
                      SYNTAX  IpAddress
                      ACCESS  read-write
                      STATUS  mandatory
                      DESCRIPTION
                      "Contains the subnet mask for the ethernet interface"
                      ::= { extEthernetInterface 14 }

         -- ********************************************************************************
         -- DHCP Server Assigned Settings for ethernet interface 1
         -- ********************************************************************************

         -- 4.9.1.x.16
         dhcpEthernetInterface  OBJECT IDENTIFIER ::= { extEthernetInterface 16 }

          -- 4.9.1.x.16.1
          dhcpHostName  OBJECT-TYPE
                       SYNTAX  OCTET STRING (SIZE(0..64))
                       ACCESS  read-only
                       STATUS  mandatory
                       DESCRIPTION
                       "Contains the 64 byte null terminated DNS host name for this
                       interface, assigned by the DHCP server."
                       ::= { dhcpEthernetInterface 1 }

          -- 4.9.1.x.16.2
          dhcpIPAddress   OBJECT-TYPE
                       SYNTAX  IpAddress
                       ACCESS  read-only
                       STATUS  mandatory
                       DESCRIPTION
                       "Contains the IP address for the ethernet interface,
                       assigned by the DHCP server."
                       ::= { dhcpEthernetInterface 2 }

          -- 4.9.1.x.16.3
          dhcpGatewayIPAddress   OBJECT-TYPE
                       SYNTAX  IpAddress
                       ACCESS  read-only
                       STATUS  mandatory
                       DESCRIPTION
                       "Contains the IP address of the gateway/router for the ethernet
                        interface, assigned by the DHCP server."
                       ::= { dhcpEthernetInterface 3 }

          -- 4.9.1.x.16.4
          dhcpSubnetMask   OBJECT-TYPE
                       SYNTAX  IpAddress
                       ACCESS  read-only
                       STATUS  mandatory
                       DESCRIPTION
                       "Contains the Subnet Mask for the ethernet
                       interface, assigned by the DHCP server."
                       ::= { dhcpEthernetInterface 4 }

          -- 4.9.1.x.16.5
          dhcpDomainName  OBJECT-TYPE
                       SYNTAX  OCTET STRING (SIZE(0..64))
                       ACCESS  read-only
                       STATUS  mandatory
                       DESCRIPTION
                       "Contains the 64 byte null terminated Domain Name for this
                       interface, assigned by the DHCP server."
                       ::= { dhcpEthernetInterface 5 }

          -- 4.9.1.x.16.6
          dhcpDHCPServer  OBJECT-TYPE
                       SYNTAX  IpAddress
                       ACCESS  read-only
                       STATUS  mandatory
                       DESCRIPTION
                       "Contains the DHCP server IP address used to acquire the
                       DHCP settings."
                       ::= { dhcpEthernetInterface 6 }

          -- 4.9.1.x.16.7
          dhcpPrimaryDNSServer  OBJECT-TYPE
                       SYNTAX  IpAddress
                       ACCESS  read-only
                       STATUS  mandatory
                       DESCRIPTION
                       "Contains the Primary DNS server, assigned by the DHCP server."
                       ::= { dhcpEthernetInterface 7 }

          -- 4.9.1.x.16.8
          dhcpSecondaryDNSServer  OBJECT-TYPE
                       SYNTAX  IpAddress
                       ACCESS  read-only
                       STATUS  mandatory
                       DESCRIPTION
                       "Contains the Secondary DNS server, assigned by the DHCP server."
                       ::= { dhcpEthernetInterface 8 }

          -- 4.9.1.x.16.9
          dhcpTertiaryDNSServer  OBJECT-TYPE
                       SYNTAX  IpAddress
                       ACCESS  read-only
                       STATUS  mandatory
                       DESCRIPTION
                       "Contains the tertiary DNS server, assigned by the DHCP server."
                       ::= { dhcpEthernetInterface 9 }

        -- ********************************************************************************
        -- PPP Interface 1
        -- ********************************************************************************
        -- 4.9.1.x.16
        intEthernetInterface  OBJECT IDENTIFIER ::= { networkInterfaces 2 }

         -- 4.9.1.2.1
         intEthernetInterfaceType     OBJECT-TYPE
                      SYNTAX  OCTET STRING (SIZE(0..16))
                      ACCESS  read-only
                      STATUS  mandatory
                      DESCRIPTION
                      "The type of interface.  Indicates 'PPP-1'."
                      ::= { intEthernetInterface 1 }

         -- 4.9.1.2.2
         intEthernetInterfaceEnabled  OBJECT-TYPE
                      SYNTAX  INTEGER {
                        interfaceDisabled(0),
                        interfaceEnabled(1)
                      }
                      ACCESS  read-write
                      STATUS  mandatory
                      DESCRIPTION
                      "Disable or enable the internal ethernet interface.
                      Note:  To alter any of the configuration settings for the
                      ethernet interface, the following procedure should be used:
                      (1) This object should be set to 'interfaceDisabled'
                      (2) Make the modifications to other settings
                      (3) This object should be set to 'interfaceEnabled'
                      (4) Restart the remote supervisor adapter

                      Also note that when attempting to enable this interface, the
                      remote IP address is verified to be nonzero.  If this verification
                      fails, an error response will be returned and the internal ethernet
                      interface will be left disabled."
                      ::= { intEthernetInterface 2 }

         -- 4.9.1.2.4
         intEthernetInterfaceLocalIPAddress   OBJECT-TYPE
                      SYNTAX  IpAddress
                      ACCESS  read-write
                      STATUS  mandatory
                      DESCRIPTION
                      "Contains the IP address for the MM side of the internal ethernet link."
                      ::= { intEthernetInterface 4 }

         -- 4.9.1.2.5
         intEthernetInterfaceDataRate   OBJECT-TYPE
                      SYNTAX  INTEGER {
                        enet10Megabit(3),
                        enet100Megabit(4),
                        autoSpeed(5)
                      }
                      ACCESS  read-only
                      STATUS  mandatory
                      DESCRIPTION
                      "Specifies the data transfer rate to be used over the ethernet
                      interface:  10Mb, 100Mb, or Auto."
                      ::= { intEthernetInterface 5 }

         -- 4.9.1.2.6
         intEthernetInterfaceDuplexSetting  OBJECT-TYPE
                      SYNTAX  INTEGER {
                        fullDuplex(1),
                        halfDuplex(2),
                        autoDuplex(3)
                      }
                      ACCESS  read-only
                      STATUS  mandatory
                      DESCRIPTION
                      "Specifies the duplex settings for the data transfer rate to be used over
                      the ethernet interface:  Half, Full, or Auto."
                      ::= { intEthernetInterface 6 }

         -- 4.9.1.2.7
         intEthernetInterfaceLAA OBJECT-TYPE
                      SYNTAX  OCTET STRING (SIZE(17))
                      ACCESS  read-write
                      STATUS  mandatory
                      DESCRIPTION
                     "Specifies the locally administered MAC address.  The locally administered
                      address must be a hexadecimal value between 000000000000 - FFFFFFFFFFFF.  This
                      value must be in the form XX:XX:XX:XX:XX:XX where 'X' is a number between 0 - 9 and
                      A - F.  This MM subsystem does not allow use of a multicast address.  A multicast
                      address has the least significant bit of the first byte set to a 1.  The first
                      byte must, therefore, be an even number."
                      ::= { intEthernetInterface 7 }

         -- 4.9.1.2.9
         intEthernetInterfaceGatewayIPAddress   OBJECT-TYPE
                      SYNTAX  IpAddress
                      ACCESS  read-write
                      STATUS  mandatory
                      DESCRIPTION
                      "Contains the IP address of the gateway/router for the ethernet
                       interface."
                      ::= { intEthernetInterface 9 }

         -- 4.9.1.2.10
         intEthernetInterfaceBIA OBJECT-TYPE
                      SYNTAX  OCTET STRING (SIZE(17))
                      ACCESS  read-only
                      STATUS  mandatory
                      DESCRIPTION
                      "Specifies the burned-in MAC (BIA) address."
                      ::= { intEthernetInterface 10 }

         -- 4.9.1.2.13
         intEthernetInterfaceMTU   OBJECT-TYPE
                      SYNTAX  INTEGER
                      ACCESS  read-only
                      STATUS  mandatory
                      DESCRIPTION
                      "Contains the Maximum Transmission Unit(MTU) for the ethernet
                      interface"
                      ::= { intEthernetInterface 13 }

         -- 4.9.1.2.14
         intEthernetInterfaceSubnetMask   OBJECT-TYPE
                      SYNTAX  IpAddress
                      ACCESS  read-write
                      STATUS  mandatory
                      DESCRIPTION
                      "Contains the subnet mask for the ethernet interface."
                      ::= { intEthernetInterface 14 }

       -- ********************************************************************************
       -- TCP/IP Protocol Configuration
       -- ********************************************************************************
       -- 4.9.3
       tcpProtocols  OBJECT IDENTIFIER ::= { networkConfiguration 3 }

        -- ********************************************************************************
        -- SNMP Agent Configuration
        -- ********************************************************************************
        -- 4.9.3.1
        snmpAgentConfig  OBJECT IDENTIFIER ::= { tcpProtocols 1 }


         -- 4.9.3.1.1
         snmpSystemContact     OBJECT-TYPE
                      SYNTAX  OCTET STRING (SIZE(0..48))
                      ACCESS  read-write
                      STATUS  mandatory
                      DESCRIPTION
                      "A NULL terminated 48 byte string that contains the
                      SNMP agent contact name.  Note:  Set snmpSystemAgentEnable
                      to disabled before performing a set of this object."
                      ::= { snmpAgentConfig 1 }

         -- 4.9.3.1.2
         snmpSystemLocation     OBJECT-TYPE
                      SYNTAX  OCTET STRING (SIZE(0..48))
                      ACCESS  read-write
                      STATUS  mandatory
                      DESCRIPTION
                      "A NULL terminated 48 byte string that contains the
                      SNMP agent location name.  Note:  Set snmpSystemAgentEnable
                      to disabled before performing a set of this object."
                      ::= { snmpAgentConfig 2 }

         -- 4.9.3.1.3
         snmpSystemAgentTrapsDisable  OBJECT-TYPE
                      SYNTAX  INTEGER {
                        trapsEnabled(0),
                        trapsDisabled(1)
                      }
                      ACCESS  read-write
                      STATUS  mandatory
                      DESCRIPTION
                      "Disable or enable SNMP traps.  Note:  Set snmpSystemAgentEnable
                      to disabled before performing a set of this object."
                      ::= { snmpAgentConfig 3 }

         -- ********************************************************************************
         -- SNMP Agent Community Configuration
         -- ********************************************************************************
         -- 4.9.3.1.4
         snmpAgentCommunityConfig  OBJECT IDENTIFIER ::= { snmpAgentConfig 4 }


          -- ********************************************************************************
          -- SNMP Community Configuration table
          -- ********************************************************************************

          snmpCommunityTable  OBJECT-TYPE
                                SYNTAX  SEQUENCE OF SnmpCommunityEntry
                                ACCESS  not-accessible
                                STATUS  mandatory
                                DESCRIPTION
                                "Table of SNMP Community entries"
                                ::= {  snmpAgentCommunityConfig 1 }

          snmpCommunityEntry  OBJECT-TYPE
                                SYNTAX  SnmpCommunityEntry
                                ACCESS  not-accessible
                                STATUS  mandatory
                                DESCRIPTION
                                "SNMP community entries"
                                INDEX { snmpCommunityEntryIndex }
                                ::= { snmpCommunityTable 1 }

          SnmpCommunityEntry ::= SEQUENCE {
                       snmpCommunityEntryIndex INTEGER(0..255),
                       snmpCommunityEntryCommunityName OCTET STRING (SIZE(0..15)),
                       snmpCommunityEntryCommunityIpAddress1 OCTET STRING (SIZE(0..63)),
                       snmpCommunityEntryCommunityIpAddress2 OCTET STRING (SIZE(0..63)),
                       snmpCommunityEntryCommunityIpAddress3 OCTET STRING (SIZE(0..63)),
                       snmpCommunityEntryCommunityViewType INTEGER(1..3)
          }


          snmpCommunityEntryIndex   OBJECT-TYPE
                                    SYNTAX  INTEGER(0..255)
                                    ACCESS  read-only
                                    STATUS  mandatory
                                    DESCRIPTION
                                    "Index for SNMP Agent Community entry."
                                    ::= { snmpCommunityEntry 1 }

          -- 4.9.3.1.4.1
          snmpCommunityEntryCommunityName  OBJECT-TYPE
                                    SYNTAX  OCTET STRING (SIZE(0..15))
                                    ACCESS  read-write
                                    STATUS  mandatory
                                    DESCRIPTION
                                    "SNMP Community entry name.  If an IP address of 0.0.0.0 is 
                                    configured for the first host name in the first community,
                                    any hosts can query MIB objects.  Note:  Set snmpSystemAgentEnable
                                    to disabled before performing a set of this object."
                                    ::= { snmpCommunityEntry 2 }

          -- 4.9.3.1.4.2
          snmpCommunityEntryCommunityIpAddress1  OBJECT-TYPE
                                    SYNTAX  OCTET STRING (SIZE(0..63))
                                    ACCESS  read-write
                                    STATUS  mandatory
                                    DESCRIPTION
                                    "SNMP Community IP address or host name.
                                    Can either be a dotted decimal IP string (eg. 9.37.44.2)
                                    or if DNS is enabled a host name.  If an IP address of 
                                    0.0.0.0 is configured for the first host name in the first 
                                    community,any hosts can query MIB objects.  Note:  Set
                                    snmpSystemAgentEnable to disabled before performing a
                                    set of this object."
                                    ::= { snmpCommunityEntry 3 }

          -- 4.9.3.1.4.3
          snmpCommunityEntryCommunityIpAddress2  OBJECT-TYPE
                                    SYNTAX  OCTET STRING (SIZE(0..63))
                                    ACCESS  read-write
                                    STATUS  mandatory
                                    DESCRIPTION
                                    "SNMP Community IP address or host name.
                                    Can either be a dotted decimal IP string (eg. 9.37.44.2)
                                    or if DNS is enabled a host name.  Note:  Set
                                    snmpSystemAgentEnable to disabled before performing a
                                    set of this object."
                                    ::= { snmpCommunityEntry 4 }

          -- 4.9.3.1.4.4
          snmpCommunityEntryCommunityIpAddress3  OBJECT-TYPE
                                    SYNTAX  OCTET STRING (SIZE(0..63))
                                    ACCESS  read-write
                                    STATUS  mandatory
                                    DESCRIPTION
                                    "SNMP Community IP address or host name.
                                    Can either be a dotted decimal IP string (eg. 9.37.44.2)
                                    or if DNS is enabled a host name.  Note:  Set
                                    snmpSystemAgentEnable to disabled before performing a
                                    set of this object."
                                    ::= { snmpCommunityEntry 5 }


          -- 4.9.3.1.4.5
          snmpCommunityEntryCommunityViewType  OBJECT-TYPE
                                     SYNTAX  INTEGER {
                                     read-Traps(1),
                                     write-Read-Traps(2),
                                     traps-Only(3)
                                     }
                                     ACCESS  read-write
                                     STATUS  mandatory
                                     DESCRIPTION
                                     "Access Level of the SNMPv1 managers.  Note this parameter 
                                     is set for each community.  Therefore all three managers 
                                     in the same community have the same access level."
                                     ::= { snmpCommunityEntry 6 }
                                    
         -- 4.9.3.1.5
         snmpv1SystemAgentEnable  OBJECT-TYPE
                      SYNTAX  INTEGER {
                        disabled(0),
                        enabled(1)
                      }
                      ACCESS  read-write
                      STATUS  mandatory
                      DESCRIPTION
                      "Disable or enable the SNMPv1 agent.

                      Note:  To alter any of the configuration settings for the SNMPv1
                      agent, the following procedure should be used:
                      (1) This object should be set to 'disabled'
                      (2) Make the modifications to other settings
                      (3) This object should be set to 'enabled'
                      (4) Restart the remote supervisor adapter if this mib is changed 
                      with respect to the value at system bootup time.  For example the 
                      SNMPv1 agent was set to disabled at system bootup time and now 
                      it is enabled.  Then restarting the remote supervisor adaptor is 
                      required.  

                      Also note that when attempting to enable this agent,
                      the following are verifed:
                      (1) Is there a valid system contact
                      (2) Is there a valid system name
                      (3) Is there at least one valid community name and for that
                      community name is there one valid IP address or hostname

                      If this verification fails an error response will be returned
                      and the SNMPv1 agent will be left disabled."
                      ::= { snmpAgentConfig 5 }

         -- 4.9.3.1.6
         snmpv3SystemAgentEnable  OBJECT-TYPE
                      SYNTAX  INTEGER {
                        disabled(0),
                        enabled(1)
                      }
                      ACCESS  read-write
                      STATUS  mandatory
                      DESCRIPTION
                      "Disable or enable the SNMPv3 agent.
                      
                      Note:  To alter any of the configuration settings for the SNMPv3
                      agent, the following procedure should be used:
                      (1) This object should be set to 'disabled'
                      (2) Make the modifications to other settings
                      (3) This object should be set to 'enabled'
                      (4) Restart the remote supervisor adapter if this mib is changed 
                      with respect to the value at system bootup time.  For example the 
                      SNMPv3 agent was set to disabled at system bootup time and now 
                      it is enabled.  Then restarting the remote supervisor adaptor is 
                      required.  

                      Also note that when attempting to enable this agent,
                      the following are verifed:
                      (1) Is there a valid system contact?
                      (2) Is there a valid system name?

                      If this verification fails an error response will be returned
                      and the SNMPv3 agent will be left disabled."

                      ::= { snmpAgentConfig 6 }

         -- ********************************************************************************
         -- SNMP Agent User Profile Configuration
         -- ********************************************************************************
         
         -- 4.9.3.1.9
         snmpAgentUserProfileConfig  OBJECT IDENTIFIER ::= { snmpAgentConfig 9 }


          -- ********************************************************************************
          -- SNMP User Profile Configuration table
          -- ********************************************************************************

          snmpUserProfileTable  OBJECT-TYPE
                                SYNTAX  SEQUENCE OF SnmpUserProfileEntry
                                ACCESS  not-accessible
                                STATUS  mandatory
                                DESCRIPTION
                                "Table of SNMPv3 User Profile entries"
                                ::= {  snmpAgentUserProfileConfig 1 }

          snmpUserProfileEntry  OBJECT-TYPE
                                SYNTAX  SnmpUserProfileEntry
                                ACCESS  not-accessible
                                STATUS  mandatory
                                DESCRIPTION
                                "SNMP User Profile entries"
                                INDEX { snmpUserProfileEntryIndex }
                                ::= { snmpUserProfileTable 1 }

          SnmpUserProfileEntry ::= SEQUENCE {
                       snmpUserProfileEntryIndex INTEGER(0..255),
                       -- snmpUserProfileEntryUserName OCTET STRING (SIZE(0..31)),
                       snmpUserProfileEntryContextName OCTET STRING (SIZE(0..31)),
                       snmpUserProfileEntryAuthProt INTEGER(0..255),
                       -- snmpUserProfileEntryAuthPassword OCTET STRING (SIZE(0..31)),
                       snmpUserProfileEntryPrivProt INTEGER(0..255),
                       snmpUserProfileEntryPrivPassword OCTET STRING (SIZE(0..31)),
                       snmpUserProfileEntryViewType INTEGER(0..255),
                       snmpUserProfileEntryIpAddress OCTET STRING (SIZE(0..63))
          }


          snmpUserProfileEntryIndex   OBJECT-TYPE
                                    SYNTAX  INTEGER(0..255)
                                    ACCESS  read-only
                                    STATUS  mandatory
                                    DESCRIPTION
                                    "Index for SNMPv3 Agent User Profile entry."
                                    ::= { snmpUserProfileEntry 1 }
                                    

--          snmpUserProfileEntryUserName  OBJECT-TYPE
--                                    SYNTAX  OCTET STRING (SIZE(0..31))
--                                    ACCESS  read-write
--                                    STATUS  mandatory
--                                    DESCRIPTION
--                                    "SNMPv3 User Profile entry - User name."
--                                    ::= { snmpUserProfileEntry 2 }


          snmpUserProfileEntryContextName  OBJECT-TYPE
                                    SYNTAX  OCTET STRING (SIZE(0..31))
                                    ACCESS  read-write
                                    STATUS  mandatory
                                    DESCRIPTION 
                                    "SNMPv3 User Profile entry - Context name 
                                    for users to access MIB objects.  Note that context names can be duplicate.  
                                    They can also be shared among users if the users have the same authentication 
                                    protocol level, privacy protocol level, and view type.  In addition empty  
                                    string is the default and valid context name."                                   
                                    ::= { snmpUserProfileEntry 3 }
          
          snmpUserProfileEntryAuthProt   OBJECT-TYPE
                                    SYNTAX  INTEGER {
                                    none (1),
                                    md5 (2), 
                                    sha (3)
                                    }
                                    ACCESS  read-write
                                    STATUS  mandatory
                                    DESCRIPTION
                                    "SNMPv3 User Profile entry - Authentication Protocol 
                                    supported by the user."
                                    ::= { snmpUserProfileEntry 4 }
                                    
--           snmpUserProfileEntryAuthPassword  OBJECT-TYPE
--                                    SYNTAX  OCTET STRING (SIZE(0..31))
--                                    ACCESS  read-write
--                                    STATUS  mandatory
--                                    DESCRIPTION
--                                    "SNMPv3 User Profile entry - Authentication password 
--                                    for the user."
--                                    ::= { snmpUserProfileEntry 5 }
                                    
            snmpUserProfileEntryPrivProt   OBJECT-TYPE
                                    SYNTAX  INTEGER {
                                    none (1),
                                    des (2)
                                    }
                                    ACCESS  read-write
                                    STATUS  mandatory
                                    DESCRIPTION
                                    "SNMPv3 User Profile entry - Privacy Protocol 
                                    supported by the user."
                                    ::= { snmpUserProfileEntry 6 }
                                    
           snmpUserProfileEntryPrivPassword  OBJECT-TYPE
                                    SYNTAX  OCTET STRING (SIZE(0..31))
                                    ACCESS  read-write
                                    STATUS  mandatory
                                    DESCRIPTION
                                    "SNMPv3 User Profile entry - Privacy password 
                                    for the user.
                                    
                                    NOTE: Value returned for the GET command is 
                                    meaningless for this MIB for security reason."
                                    ::= { snmpUserProfileEntry 7 }

            snmpUserProfileEntryViewType   OBJECT-TYPE
                                    SYNTAX  INTEGER {
                                    read-Traps(1),
                                    read-Write-Traps(2),
                                    traps-Only(3)
                                    }
                                    ACCESS  read-write
                                    STATUS  mandatory
                                    DESCRIPTION
                                    "SNMPv3 User Profile entry - Access level (Get, Set, and 
                                    Traps) of the user. "
                                    ::= { snmpUserProfileEntry 8 }
                                    

           snmpUserProfileEntryIpAddress  OBJECT-TYPE
                                    SYNTAX  OCTET STRING (SIZE(0..63))
                                    ACCESS  read-write
                                    STATUS  mandatory
                                    DESCRIPTION
                                    "SNMPv3 User Profile entry - IP address or host name.
                                    Can either be a dotted decimal IP string (eg. 9.37.44.2)
                                    or if DNS is enabled a host name."
                                    ::= { snmpUserProfileEntry 9 }
        
        -- ********************************************************************************
        -- DNS Configuration
        -- ********************************************************************************
        -- 4.9.3.2
        dnsConfig  OBJECT IDENTIFIER ::= { tcpProtocols 2 }

         -- 4.9.3.2.1
         dnsEnabled   OBJECT-TYPE
                      SYNTAX  INTEGER {
                        dnsDisabled(0),
                        dnsEnabled(1)
                      }
                      ACCESS  read-write
                      STATUS  mandatory
                      DESCRIPTION
                      "Disable or enable the DNS agent.

                      Note:  To alter any of the configuration settings for the DNS agent,
                      the following procedure should be used:
                      (1) This object should be set to 'disabled'
                      (2) Make the modifications to other settings
                      (3) This object should be set to 'enabled'
                      (4) Restart the remote supervisor adapter

                      Also note that when attempting to enable this agent, it is verified
                      that there is at least one valid DNS server IP address.  If this
                      verification fails, an error response will be returned and the DNS
                      agent will be left disabled."
                      ::= { dnsConfig 1 }

         -- 4.9.3.2.2
         dnsServerIPAddress1   OBJECT-TYPE
                      SYNTAX  IpAddress
                      ACCESS  read-write
                      STATUS  mandatory
                      DESCRIPTION
                      "Contains the primary DNS server IP address."
                      ::= { dnsConfig 2 }

         -- 4.9.3.2.3
         dnsServerIPAddress2   OBJECT-TYPE
                      SYNTAX  IpAddress
                      ACCESS  read-write
                      STATUS  mandatory
                      DESCRIPTION
                      "Contains the secondary DNS server IP address."
                      ::= { dnsConfig 3 }

         -- 4.9.3.2.4
         dnsServerIPAddress3   OBJECT-TYPE
                      SYNTAX  IpAddress
                      ACCESS  read-write
                      STATUS  mandatory
                      DESCRIPTION
                      "Contains the tertiary DNS server IP address."
                      ::= { dnsConfig 4 }


        -- ********************************************************************************
        -- SMTP Configuration
        -- ********************************************************************************
        -- 4.9.3.3
        smtpConfig  OBJECT IDENTIFIER ::= { tcpProtocols 3 }


        -- 4.9.3.3.1
         smtpServerNameOrIPAddress     OBJECT-TYPE
                      SYNTAX  OCTET STRING (SIZE(0..64))
                      ACCESS  read-write
                      STATUS  mandatory
                      DESCRIPTION
                      "A NULL terminated 64 byte string that contains the
                      SMTP server host name or IP address (a.b.c.d)."
                      ::= { smtpConfig 1 }

        -- 4.9.3.3.2
         attachmentsToEmailAlerts  OBJECT-TYPE
                      SYNTAX  INTEGER {
                        noAttachments(0),
                        attachEventLog(1)
                      }
                      ACCESS  read-write
                      STATUS  mandatory
                      DESCRIPTION
                      "Indicates if the event log should be attached to
                      an email alert."
                      ::= { smtpConfig 2 }


        -- 4.9.3.4.1
        tcpApplicationConfig  OBJECT IDENTIFIER ::= { tcpProtocols 4 }
         telnetInactivityTimeout  OBJECT-TYPE
                      SYNTAX  INTEGER
                      ACCESS  read-write
                      STATUS  mandatory
                      DESCRIPTION
                      "Default is 120 seconds. Value of zero is no timeout.
                      Max value is any positive 4 bytes value."
                      ::= { tcpApplicationConfig 1 }

        -- 4.9.3.4.2
         commandModeInactivityTimeout  OBJECT-TYPE
                      SYNTAX  INTEGER
                      ACCESS  read-write
                      STATUS  mandatory
                      DESCRIPTION
                      "Default is zero means no timeout. Max value is any positive 4 bytes value."
                      ::= { tcpApplicationConfig 2 }

        -- 4.9.3.4.4
         commandModeEnable  OBJECT-TYPE
                      SYNTAX  INTEGER {
                        disabled(0),
                        enabled(1)
                      }
                      ACCESS  read-write
                      STATUS  mandatory
                      DESCRIPTION
                      "Disable/Enable TCP Command Mode."
                      ::= { tcpApplicationConfig 4 }
        
        -- 4.9.3.4.5
         slpAddrType  OBJECT-TYPE
                      SYNTAX  INTEGER {
                        multicast(0),
                        broadcast(1)
                      }
                      ACCESS  read-write
                      STATUS  mandatory
                      DESCRIPTION
                      "Set SLP address type to 0 (multicast) or 1 (broadcast). Note that when
                      slpAddrType is set to broadast value then the multicast address set in in
                      slpMulticastAddt will be ignored."
                      ::= { tcpApplicationConfig 5 }

        -- 4.9.3.4.6
         slpMulticastAddr  OBJECT-TYPE
                      SYNTAX  IpAddress
                      ACCESS  read-write
                      STATUS  mandatory
                      DESCRIPTION
                      "Service Locator Protocol Multicast address"
                      ::= { tcpApplicationConfig 6 }

        -- 4.9.3.5.x  TCP Port Assignment
        tcpPortAssignmentCfg    OBJECT IDENTIFIER ::= { tcpProtocols 5 } 
     
         tcpPortsRestoreDefault   OBJECT-TYPE
                      SYNTAX  INTEGER 
                      ACCESS  read-write
                      STATUS  mandatory
                      DESCRIPTION
                      "HTTP port number. Default value is 80. Once changed, the url's have to 
                      include :port at the end. MM has to be reset for change to take effect.
                      
                      NOTE: Value returned for the GET command is meaningless for this 
                      MIB."
                      ::= { tcpPortAssignmentCfg 1 }
                   
         httpPortAssignment   OBJECT-TYPE
                      SYNTAX  INTEGER 
                      ACCESS  read-write
                      STATUS  mandatory
                      DESCRIPTION
                      "HTTP port number. Default value is 80. Once changed, the url's have to 
                      include :port at the end. MM has to be reset for change to take effect."
                      ::= { tcpPortAssignmentCfg 2 }
                   
         httpsPortAssignment   OBJECT-TYPE
                      SYNTAX  INTEGER 
                      ACCESS  read-write
                      STATUS  mandatory
                      DESCRIPTION
                      "SSL port number. Default value is 443. Once changed, the url's have to 
                      include :port at the end. MM has to be reset for change to take effect."
                      ::= { tcpPortAssignmentCfg 3 }
                   
         telnetPortAssignment   OBJECT-TYPE
                      SYNTAX  INTEGER 
                      ACCESS  read-write
                      STATUS  mandatory
                      DESCRIPTION
                      "telnet port number. Default value is 23. MM has to be reset for change 
                      to take effect."
                      ::= { tcpPortAssignmentCfg 4 }
                   
         sshPortAssignment   OBJECT-TYPE
                      SYNTAX  INTEGER 
                      ACCESS  read-write
                      STATUS  mandatory
                      DESCRIPTION
                      "SSH port number. Default value is 22. MM has to be reset for change 
                      to take effect."
                      ::= { tcpPortAssignmentCfg 5 }
                   
         snmpAgentPortAssignment   OBJECT-TYPE
                      SYNTAX  INTEGER 
                      ACCESS  read-write
                      STATUS  mandatory
                      DESCRIPTION
                      "SNMP Agent port number. Default value is 161. MM has to be reset for change 
                      to take effect."
                      ::= { tcpPortAssignmentCfg 6 }
                   
         snmpTrapsPortAssignment   OBJECT-TYPE
                      SYNTAX  INTEGER 
                      ACCESS  read-write
                      STATUS  mandatory
                      DESCRIPTION
                      "SNMP Traps port number. Default value is 162. MM has to be reset for change 
                      to take effect."
                      ::= { tcpPortAssignmentCfg 7 }
                   
        
        -- 4.9.3.6.x  LDAP Client Configuration
        ldapClientCfg    OBJECT IDENTIFIER ::= { tcpProtocols 6 } 
        
         -- 4.9.3.6.1
         ldapServer1NameOrIPAddress     OBJECT-TYPE
                      SYNTAX  OCTET STRING (SIZE(0..64))
                      ACCESS  read-write
                      STATUS  mandatory
                      DESCRIPTION
                      "A NULL terminated 64 byte string that contains the
                      LDAP server host name or IP address (a.b.c.d)."
                      ::= { ldapClientCfg 1 }

         -- 4.9.3.6.2
         ldapServer1PortNumber   OBJECT-TYPE
                      SYNTAX  INTEGER 
                      ACCESS  read-write
                      STATUS  mandatory
                      DESCRIPTION
                      "LDAP server port number."
                      ::= { ldapClientCfg 2 }
                   
         -- 4.9.3.6.3
         ldapServer2NameOrIPAddress     OBJECT-TYPE
                      SYNTAX  OCTET STRING (SIZE(0..64))
                      ACCESS  read-write
                      STATUS  mandatory
                      DESCRIPTION
                      "A NULL terminated 64 byte string that contains the
                      LDAP server host name or IP address (a.b.c.d)."
                      ::= { ldapClientCfg 3 }

         -- 4.9.3.6.4
         ldapServer2PortNumber   OBJECT-TYPE
                      SYNTAX  INTEGER 
                      ACCESS  read-write
                      STATUS  mandatory
                      DESCRIPTION
                      "LDAP server port number."
                      ::= { ldapClientCfg 4 }
                   
         -- 4.9.3.6.5
         ldapServer3NameOrIPAddress     OBJECT-TYPE
                      SYNTAX  OCTET STRING (SIZE(0..64))
                      ACCESS  read-write
                      STATUS  mandatory
                      DESCRIPTION
                      "A NULL terminated 64 byte string that contains the
                      LDAP server host name or IP address (a.b.c.d)."
                      ::= { ldapClientCfg 5 }

         -- 4.9.3.6.6
         ldapServer3PortNumber   OBJECT-TYPE
                      SYNTAX  INTEGER 
                      ACCESS  read-write
                      STATUS  mandatory
                      DESCRIPTION
                      "LDAP server port number."
                      ::= { ldapClientCfg 6 }
                   
         -- 4.9.3.6.7
         ldapRootDN     OBJECT-TYPE
                      SYNTAX  OCTET STRING (SIZE(0..64))
                      ACCESS  read-write
                      STATUS  mandatory
                      DESCRIPTION
                      "Distinguished Name for root entry of directory tree. 
                      An example might look like dn=foobar,dn=com."
                      ::= { ldapClientCfg 7 }

         -- 4.9.3.6.8
         ldapUserSearchBaseDN     OBJECT-TYPE
                      SYNTAX  OCTET STRING (SIZE(0..64))
                      ACCESS  read-write
                      STATUS  mandatory
                      DESCRIPTION
                      "As part of the user authentication process, it is necessary to search 
                      the LDAP server for one or more attributes associated with a particular 
                      user. Any search request must specify the base DN for the actual search. 
                      This field specifies the base DN which should be used to search the User 
                      directory. An example might look like cn=users,dn=foobar,dn=com. If this 
                      field is left blank, the Root DN will be used as the search base instead.
                      As mentioned, user searches are part of the authentication process. They 
                      are carried out to retrieve information about the user such as login 
                      permissions, callback number, and group memberships. For Version 2.0 LDAP 
                      clients, it is strongly encouraged that this parameter be configured, 
                      otherwise a search using the root DN may not succeed (as seen on Active 
                      Directory servers)."
                      ::= { ldapClientCfg 8 }

         -- 4.9.3.6.9
         ldapGroupFilter     OBJECT-TYPE
                      SYNTAX  OCTET STRING (SIZE(0..64))
                      ACCESS  read-write
                      STATUS  mandatory
                      DESCRIPTION
                      "This filter is used for group authentication. It specifies what group or 
                      groups that this MM belongs to. If left blank, group authentication is 
                      disabled. Otherwise, group authentication will be performed against the 
                      filter. The filter can be a specific group name (eg. RSAWest), a wildcard (*) 
                      which matches everything, or a wildcard with a prefix (eg. RSA*). The default 
                      filter is RSA*. 
                      After user authentication, group authentication will take place, whereby an 
                      attempt will be made to match the group or groups (that the user belongs to) 
                      to the group filter defined here. If there is no match, the user will not pass 
                      authentication and will be blocked. If there is a match, the login permissions 
                      for the user will be retrieved from the matched group(s), unless the user 
                      already has login permissions assigned directly from the user record retrieved 
                      from the LDAP server."
                      ::= { ldapClientCfg 9 }

         -- 4.9.3.6.10
         ldapBindingMethod  OBJECT-TYPE
                      SYNTAX  INTEGER {
                        anonymousAuthentication(0),
                        clientAuthentication(1),
                        userPrincipalName(2),
                        strictUserPrincipalName(3)
                      }
                      ACCESS  read-write
                      STATUS  mandatory
                      DESCRIPTION
                      "On initial binds to the LDAP server during user authentication, there are 
                      three options:
                      Anonymous authentication: Bind attempt is made without a client DN or password. 
                      If the bind is successful, a search will be requested in order to find an entry 
                      on the LDAP server for the user attempting to login. If an entry is found, a 
                      second attempt to bind will be attempted, this time with the user's DN and 
                      password. If this succeeds, the user is deemed to have passed the user 
                      authentication phase. Group authentication is then attempted if it is enabled.
                      Client authentication: Bind attempt is made with client DN and password 
                      specified by this configuration parameter. If the bind is successful, we 
                      proceed as above.
                      User Principal Name (UPN): Bind attempt is made directly with the credentials 
                      used during the login process. If this succeeds, the user is deemed to have 
                      passed the user authentication phase. Note that for Active Directory servers, 
                      the userid can have the form someuser@somedomain or simply someuser.
                      Strict UPN: This is the same as UPN above, except that the userid must have 
                      the form someuser@somedomain. The string entered by the user will be parsed 
                      for the @ symbol."
                      ::= { ldapClientCfg 10 }

         -- 4.9.3.6.11
         ldapClientAuthenticationDN     OBJECT-TYPE
                      SYNTAX  OCTET STRING (SIZE(0..64))
                      ACCESS  read-write
                      STATUS  mandatory
                      DESCRIPTION
                      "The initial bind to the LDAP server during user authentication can be 
                      performed with anonymous authentication, client based authentication, or UPN. 
                      The client based option requires a client DN and password as parameters to 
                      the bind request. These parameters are configured here. Note that the password 
                      can be left blank."
                      ::= { ldapClientCfg 11 }

         -- 4.9.3.6.12
         ldapClientAuthenticationPassword     OBJECT-TYPE
                      SYNTAX  OCTET STRING (SIZE(0..16))
                      ACCESS  read-write
                      STATUS  mandatory
                      DESCRIPTION
                      "The client authentication password"
                      ::= { ldapClientCfg 12 }

         -- 4.9.3.6.13
         ldapUIDsearchAttribute     OBJECT-TYPE
                      SYNTAX  OCTET STRING (SIZE(0..64))
                      ACCESS  read-write
                      STATUS  mandatory
                      DESCRIPTION
                      "When the binding method selected is Anonymous authentication or Client 
                      authentication, the initial bind to the LDAP server is followed by a search 
                      request aimed at retrieving specific information about the user, including the 
                      user's DN, login permissions, and group ownerships. In order to retrieve this 
                      information, the search request must specify the attribute name used to 
                      represent userids on that server. Specifically, this name is used as a search 
                      filter against the login id entered by the user. This attribute name is 
                      configured here. If this field is left blank, a default of uid is used during 
                      user authentication. 
                      For example, on Active Directory servers, the attribute name used for userids 
                      is often sAMAccoutName. 
                      When the binding method selected is UPN or Strict UPN, this field defaults 
                      automatically to userPrincipalName during user authentication if the userid 
                      entered has the form userid@somedomain."
                      ::= { ldapClientCfg 13 }

         -- 4.9.3.6.14
         ldapGroupSearchAttribute     OBJECT-TYPE
                      SYNTAX  OCTET STRING (SIZE(0..64))
                      ACCESS  read-write
                      STATUS  mandatory
                      DESCRIPTION
                      "When the MM Group Filter name is configured, it is necessary to retrieve 
                      from the LDAP server the list of groups that a particular user belongs to. 
                      This is required to do group authentication. In order to retrieve this list, 
                      the search filter sent to the server must specify the attribute name associated 
                      with groups. This field specifies this attribute name. 
                      If this field is left blank, the attribute name in the filter will default 
                      to memberOf."
                      ::= { ldapClientCfg 14 }

         -- 4.9.3.6.15
         ldapLoginPermissionAttribute     OBJECT-TYPE
                      SYNTAX  OCTET STRING (SIZE(0..64))
                      ACCESS  read-write
                      STATUS  mandatory
                      DESCRIPTION
                      "When a user successfully authenticates via a LDAP server, it is necessary 
                      to retrieve the login permissions for this user. In order to retrieve these 
                      permissions, the search filter sent to the server must specify the attribute 
                      name associated with login permissions. This field specifies this attribute 
                      name."
                      ::= { ldapClientCfg 15 }

         -- 4.9.3.6.16
         ldapUseDNSOrPreConfiguredServers     OBJECT-TYPE
                      SYNTAX  INTEGER {
                        usePreConfiguredLDAPServers (0),
                        useDNSToFindLDAPServers (1)
                      }
                      ACCESS  read-write
                      STATUS  mandatory
                      DESCRIPTION
                      "The MM contains a Version 2.0 LDAP Client that may be configured to provide 
                      user authentication through one or more LDAP servers. The LDAP server(s) to be 
                      used for authentication can be discovered dynamically or manually pre-configured. 
                      
                      If the usePreConfiguredLDAPServers option is selected, up to 3 LDAP servers can 
                      be configured. Simply enter the server's IP address or hostname (assuming DNS 
                      is enabled).  The port number for each server is optional. If left blank, 
                      the default value of 389 is used for non-secured LDAP connections. For secured 
                      connections, the default is 636. At least one server must be configured.
                      
                      If the useDNSToFindLDAPServers is selected, the mechanisms described by RFC2782 
                      (A DNS RR for specifying the location of services) are applied to find the 
                      server(s). This is known as DNS SRV."
                      ::= { ldapClientCfg 16 }
         
         -- 4.9.3.6.17
         ldapDomainSource     OBJECT-TYPE
                      SYNTAX  INTEGER {
                        extractSearchDomainFromLoginID (0),
                        useOnlyConfiguredSearchDomainBelow (1),
                        tryLoginFirstThenConfiguredValue (2)
                      }
                      ACCESS  read-write
                      STATUS  mandatory
                      DESCRIPTION
                      "The DNS SRV request sent to the DNS server must specify a domain name. 
                      The LDAP client will determine where to get this domain name based on one 
                      of the following three options: 
                      
                        - extractSearchDomainFromLoginID: With this option, the LDAP client will 
                      use the domain name in the login id. For example, if the login id is 
                      joesmith@mycompany.com, the domain name equals mycompany.com. If the domain 
                      name cannot be extracted, the DNS SRV will fail, causing the user 
                      authentication to fail automatically.
                      
                        - useOnlyConfiguredSearchDomainBelow: With this option, the LDAP client 
                      will use the domain name configured in the Search Domain parameter. 
                      
                        - tryLoginFirstThenConfiguredValue: With this option, the LDAP client will 
                      first attempt to extract the domain name from the login id. If this succeeds, 
                      this domain name will be used in the DNS SRV request. If there is no domain 
                      name present in the login id, the LDAP client will instead use the configured 
                      Search Domain parameter as the domain name in the DNS SRV request. 
                      If nothing is configured, user authentication will fail immediately."
                      ::= { ldapClientCfg 17 }

         -- 4.9.3.6.18
         ldapSearchDomain     OBJECT-TYPE
                      SYNTAX  OCTET STRING (SIZE(0..64))  
                      ACCESS  read-write
                      STATUS  mandatory
                      DESCRIPTION
                      "This parameter may be used as the domain name in the DNS SRV request, 
                      depending on how the Domain Source parameter is configured."
                      ::= { ldapClientCfg 18 }

         -- 4.9.3.6.19
         ldapServiceName     OBJECT-TYPE
                      SYNTAX  OCTET STRING (SIZE(0..16))  
                      ACCESS  read-write
                      STATUS  mandatory
                      DESCRIPTION
                      "The DNS SRV request sent to the DNS server must also specify a service name. 
                      The configured value will be used for this purpose. If left blank, the default 
                      value used is 'ldap'. Note that the DNS SRV request must also specify a protocol 
                      name. This defaults to 'tcp' and is not configurable."
                      ::= { ldapClientCfg 19 }

        -- ********************************************************************************
        -- Uplink Check Configuration
        -- ********************************************************************************
        -- 4.9.3.7
        uplinkCheckConfig  OBJECT IDENTIFIER ::= { tcpProtocols 7 }

         -- 4.9.3.7.1
         uplinkCheckEnabled   OBJECT-TYPE
                      SYNTAX  INTEGER {
                        uplinkCheckDisabled(0),
                        uplinkCheckEnabled(1)
                      }
                      ACCESS  read-write
                      STATUS  mandatory
                      DESCRIPTION
                      "Disable or enable network uplink checking."
                      ::= { uplinkCheckConfig 1 }

         -- 4.9.3.7.2
         uplinkCheckDelay   OBJECT-TYPE
                      SYNTAX  INTEGER 
                      ACCESS  read-write
                      STATUS  mandatory
                      DESCRIPTION
                      "Delay, in minutes, between discovery of a failed network uplink and
                       the subsequent MM failover."
                      ::= { uplinkCheckConfig 2 }


       -- ********************************************************************************
       -- SOL (Serial Over LAN) Configuration
       -- ********************************************************************************
       -- 4.10
       solConfiguration  OBJECT IDENTIFIER ::= { configureSP 10 }

        -- ********************************************************************************
        -- SOL Global Configuration
        -- ********************************************************************************
        -- 4.10.1
        solGlobalConfig  OBJECT IDENTIFIER ::= { solConfiguration 1 }

         -- 4.10.1.1
         solEnable  OBJECT-TYPE
                      SYNTAX  INTEGER {
                        solDisabled(0),
                        solEnabled(1)
                    }
                      ACCESS  read-write
                      STATUS  mandatory
                      DESCRIPTION
                    "Disable/Enable SOL dynamically."
                    ::= { solGlobalConfig 1 }

         -- 4.10.1.2
         solVlanId  OBJECT-TYPE
                      SYNTAX  INTEGER
                      ACCESS  read-write
                      STATUS  mandatory
                      DESCRIPTION
                    "SOL VLAN Id number. Valid number is from 1 to 4095."
                    ::= { solGlobalConfig 2 }

         -- 4.10.1.3
         solAccumulateTimeout  OBJECT-TYPE
                               SYNTAX  INTEGER
                               ACCESS  read-write
                               STATUS  mandatory
                               DESCRIPTION
                               "This value specifies how much time in milisecond SOL to buffer data before
                               sending the next SOL packet since the last SOL packet was transmitted.
                               Valid value from 5 ms to 1275 ms. The value is in 5 ms increment. Value
                               is not in 5 ms increment will be truncated to a nearest 5s. Default value
                               is 5 ms."
                               ::= { solGlobalConfig 3 }

         -- 4.10.1.4
         solCharSendThreshold  OBJECT-TYPE
                               SYNTAX  INTEGER
                               ACCESS  read-write
                               STATUS  mandatory
                               DESCRIPTION
                               "This value specifies how many characters SOL to buffer before
                               sending the next SOL packet since the last SOL packet was transmitted.
                               Valid value is from 1 to 255"
                               ::= { solGlobalConfig 4 }

         -- 4.10.1.5
         solRetry  OBJECT-TYPE
                   SYNTAX  INTEGER
                   ACCESS  read-write
                   STATUS  mandatory
                   DESCRIPTION
                   "Retry count. Valid value from 0-7. 0 means no retries after packet is transmitted.
                   Packet will be dropped if no ACK/NACK received by the time retries expired."
                   ::= { solGlobalConfig 5 }

         -- 4.10.1.6
         solRetryInterval  OBJECT-TYPE
                           SYNTAX  INTEGER
                           ACCESS  read-write
                           STATUS  mandatory
                           DESCRIPTION
                           "Retry Interval in 10 ms increment. Sets the time that the SOL will 
                           wait before the first retry and the time between retries when sending SOL 
                           packets to the remote blade. Value range is from 0 to 2550 ms in 10 ms
                           increment. 0 means retries will be sent back-to-back."
                           ::= { solGlobalConfig 6 }
                           
      solExitToCliKeySeq  OBJECT-TYPE
                      SYNTAX  OCTET STRING(SIZE(0..16))
                      ACCESS  read-write
                      STATUS  mandatory
                      DESCRIPTION
                      "This is the keystroke sequence used to escape out of SOL session and back to CLI 
                      console. This sequence must have at least one character. The caret symbol (^) 
                      has a special meaning in this sequence. It denotes 'Ctrl' for keystrokes that 
                      map to Ctrl sequences (for example, ^[ for the escape key and ^M for carriage 
                      return). All ocurrences of ^ will be interpreted as part of a Ctrl sequence. 
                      Refer to an ASCII-to-key conversion table for a complete list of Ctrl sequences. 
                      The default value for this field is '^[(' i.e. ESC followed by (."
                      ::= { solGlobalConfig 7 }
                   
      solResetBladeKeySeq  OBJECT-TYPE
                      SYNTAX  OCTET STRING(SIZE(0..16))
                      ACCESS  read-write
                      STATUS  mandatory
                      DESCRIPTION
                      "This is the keystroke sequence used to reset the blade while in SOL session 
                      console. This sequence must have at least one character. The caret symbol (^) 
                      has a special meaning in this sequence. It denotes 'Ctrl' for keystrokes that 
                      map to Ctrl sequences (for example, ^[ for the escape key and ^M for carriage 
                      return). All ocurrences of ^ will be interpreted as part of a Ctrl sequence. 
                      Refer to an ASCII-to-key conversion table for a complete list of Ctrl sequences. 
                      The default value for this field is '^[R^[r^[R' i.e. ESC R ESC r ESC R."
                      ::= { solGlobalConfig 8 }
                   

         -- 4.10.2 Blade SOL config
         solBladeConfig  OBJECT IDENTIFIER ::= { solConfiguration 2 }


         -- 4.10.2.1
         solBladeTable OBJECT-TYPE
                       SYNTAX  SEQUENCE OF SolBladeEntry
                    ACCESS  not-accessible
                    STATUS  mandatory
                    DESCRIPTION
                       "SOL Blade configuration table."
                       ::= { solBladeConfig 1 }

         -- 4.10.2.1.1
         solBladeEntry  OBJECT-TYPE
                        SYNTAX  SolBladeEntry
                       ACCESS  not-accessible
                       STATUS  mandatory
                       DESCRIPTION
                        "SOL Blade table entry"
                        INDEX { solBladeIndex }
                        ::= { solBladeTable 1 }

         SolBladeEntry ::= SEQUENCE {
                              solBladeIndex   INTEGER, 
                              solBladeName    OCTET STRING,
                              solBladeEnable  INTEGER,
                              solBladeIpAddr  IpAddress, 
                              solBladeSessionStatus  INTEGER,
                              solBladeCapability  INTEGER 
                           }

         -- 4.10.2.1.1.1
         solBladeIndex OBJECT-TYPE
                     SYNTAX  INTEGER
                     ACCESS  read-only
                     STATUS  mandatory
                     DESCRIPTION
                       "SOL Blade table index."
                       ::= { solBladeEntry 1 }

         -- 4.10.2.1.1.2
         solBladeName OBJECT-TYPE
                   SYNTAX  OCTET STRING
                   ACCESS  read-only
                   STATUS  mandatory
                   DESCRIPTION
                   "The name of the blade as a null terminated string."
                   ::= { solBladeEntry 2 }

         -- 4.10.2.1.1.3
         solBladeEnable  OBJECT-TYPE
                      SYNTAX  INTEGER {
                           solBladeDisabled(0),
                           solBladeEnabled(1)
                         }
                      ACCESS  read-write
                      STATUS  mandatory
                      DESCRIPTION
                         "Disable or enable a SOL on a blade."
                         ::= { solBladeEntry 3 }

         -- 4.10.2.1.1.4
         solBladeIpAddr   OBJECT-TYPE
                      SYNTAX  IpAddress
                     ACCESS  read-only
                     STATUS  mandatory
                     DESCRIPTION
                          "IP address of the Blade."
                          ::= { solBladeEntry 4 }

         -- 4.10.2.1.1.5
         solBladeSessionStatus OBJECT-TYPE
                      SYNTAX  INTEGER {
                                 solSessionNotReady(0),
                                 solSessionReady(1),
                                 solSessionActive(2)
                               }
                               ACCESS  read-only
                      STATUS  mandatory
                      DESCRIPTION
                               "Status of a blade SOL session:
			           solSessionNotReady: no SOL session connected to the blade.
				   solSessionReady: there is an SOL session to the blade.
				   solSessionActive: there is an SOL session to the blade and there is a
				                     client using the SOL session."
                               ::= { solBladeEntry 5 }
                               
         -- 4.10.2.1.1.6
         solBladeCapability OBJECT-TYPE
                      SYNTAX  INTEGER {
                                 notSupport(0),
                                 support(1)
                               }
                               ACCESS  read-only
                      STATUS  mandatory
                      DESCRIPTION
                               "display whether or not the blade support SOL feature."
                               ::= { solBladeEntry 6 }
                               
        -- ********************************************************************************
        -- IPMI Management
        -- ********************************************************************************
    --ipmiManagement              OBJECT IDENTIFIER ::= { configureSP 20 }

    --ipmiEnabled                 OBJECT-TYPE
    --                            SYNTAX  INTEGER {
    --                               ipmiDisabled(0),
    --                               ipmiEnabled(1)
    --                            }
    --                            ACCESS  read-write
    --                            STATUS  mandatory
    --                            DESCRIPTION
    --                            "When the setting is changed from disabled to enabled for the first time, 
    --                            the feature is started dynamically, without requiring an MM reset. However, 
    --                            when the setting is changed from enabled to disabled, the feature is not 
    --                            stopped dynamically - the MM has to be reset for the disable to take effect." 

    --                            ::= { ipmiManagement 1 }

     -- ************************************************************************
     -- BladeCenter T System Management
     -- ************************************************************************
     -- 5.1

     -- ************************************************************************
    
     telcoAlarmReq OBJECT IDENTIFIER ::= { telcoManagement 1 }


     -- ************************************************************************
     -- BladeCenter T Set A Software Alarm
     -- ************************************************************************
     -- 5.1.1
     telcoAlarmSet OBJECT-TYPE
                   SYNTAX  OCTET STRING 
                   ACCESS  read-write
                   STATUS  mandatory
                   DESCRIPTION
                   "Create a software alarm. An input octet string consists of the 
                   alarm severity level and the alarm description (40 bytes max).
                   The following severity levels are valid :
                        CRT Critical 
                        MJR Major 
                        MNR Minor
                        
                   NOTE 1: Value returned for the GET command is meaningless for 
                   this MIB.
                   
                   NOTE 2: This MIB is for BladeCenter T only."
                   ::= { telcoAlarmReq 1 }
     

     -- ************************************************************************
     -- BladeCenter T Ack an Alarm
     -- ************************************************************************
     -- 5.1.2
     telcoAlarmAck OBJECT-TYPE
                   SYNTAX  OCTET STRING 
                   ACCESS  read-write
                   STATUS  mandatory
                   DESCRIPTION
                   "Acknowledge an alarm. An input octet string consists of the 
                   alarm key ID expressed as 'mmm:aaa:ggg:iii' where: 
                      m : Module ID value of decimal digits(1-255) or 
                          blank space(s) for leading zero(s)
                      a : Alarm ID value of decimal digits(1-255) or
                          blank space(s) for leading zero(s) 
                      g : Gen ID value of decimal digits(1-255) or 
                          blank space(s) for leading zero(s)
                      i : GenInfo ID value of decimal digits(1-255) or
                          blank space(s) for leading zero(s)
                          
                   NOTE 1: Value returned for the GET command is meaningless for 
                   this MIB.
                     
                   NOTE 2: This MIB is for BladeCenter T only."
                   ::= { telcoAlarmReq 2 }
                   

     -- ************************************************************************
     -- BladeCenter T Clear an Alarm
     -- ************************************************************************
     -- 5.1.3
     telcoAlarmClear OBJECT-TYPE
                   SYNTAX  OCTET STRING 
                   ACCESS  read-write
                   STATUS  mandatory
                   DESCRIPTION
                   "Clear an active alarm. An input octet string consists of the 
                   alarm key ID expressed as 'mmm:aaa:ggg:iii' where: 
                      m : Module ID value of decimal digits(1-255) or 
                          blank space(s) for leading zero(s)
                      a : Alarm ID value of decimal digits(1-255) or
                          blank space(s) for leading zero(s) 
                      g : Gen ID value of decimal digits(1-255) or 
                          blank space(s) for leading zero(s)
                      i : GenInfo ID value of decimal digits(1-255) or
                          blank space(s) for leading zero(s)
                          
                   NOTE1 : Value returned for the GET command is meaningless for 
                   this MIB.
                     
                   NOTE 2: This MIB is for BladeCenter T only."
                   ::= { telcoAlarmReq 3 }
      


     -- ************************************************************************
     -- 5.2
     -- ************************************************************************
    
--     telcoThresholds OBJECT IDENTIFIER ::= { telcoManagement 2 }

     

     -- ************************************************************************
     -- BladeCenter T Threshold Table
     -- ************************************************************************
     -- 5.2.1

--     telcoTempThresholds OBJECT IDENTIFIER ::= { telcoThresholds 1 }


     -- ************************************************************************
     -- BladeCenter T Temperature Threshold table
     -- ************************************************************************
     -- 5.2.1.1

--     telcoTempThresholdsTable OBJECT-TYPE
--                   	      SYNTAX  SEQUENCE OF TelcoTempThresholdsEntry
--                  	      ACCESS  not-accessible
--                   	      STATUS  mandatory
--                  	      DESCRIPTION
--                   	      "Table of Temperature Threshold summary.
--                              
--                              NOTE: This MIB is for BladeCenter T only." 
--                   	      ::= { telcoTempThresholds 1 }
--
     -- ************************************************************************
     -- BladeCenter T Temperature Threshold Entries
     -- ************************************************************************
     -- 5.2.1.1.1

--     telcoTempThresholdsEntry OBJECT-TYPE
--                   	      SYNTAX TelcoTempThresholdsEntry
--                  	      ACCESS  not-accessible
--            		      STATUS  mandatory
--                   	      DESCRIPTION
--            		      "BladeCenter T Temperature Thresholds entry
--                              
--                              NOTE: This MIB is for BladeCenter T only." 
--                  	      INDEX { telcoTempThresholdsIndex }
--                   	      ::= { telcoTempThresholdsTable 1 }

--     TelcoTempThresholdsEntry  ::= SEQUENCE {
--                 	      telcoTempThresholdsIndex INTEGER,
--                            telcoTempThresholdsName  OCTET STRING, 
--                 	      telcoTempThresholdsLCRT  OCTET STRING,
--	 	              telcoTempThresholdsLCRTH OCTET STRING,
--			      telcoTempThresholdsLMJR  OCTET STRING,
--			      telcoTempThresholdsLMJRH OCTET STRING,
--                              telcoTempThresholdsLMNR  OCTET STRING,
--                              telcoTempThresholdsLMNRH OCTET STRING,
--                              telcoTempThresholdsHMNRH OCTET STRING,
--	 	              telcoTempThresholdsHMNR  OCTET STRING,
--			      telcoTempThresholdsHMJRH OCTET STRING,
--			      telcoTempThresholdsHMJR  OCTET STRING,
--                            telcoTempThresholdsHCRTH OCTET STRING,
--                            telcoTempThresholdsHCRT  OCTET STRING,
--                              telcoTempThresholdsDFT   OCTET STRING,
--                              telcoTempThresholdsLHyst OCTET STRING,
--                              telcoTempThresholdsHHyst OCTET STRING
--		              }

     -- ************************************************************************
     -- BladeCenter T Temperature Threshold Entry - Index
     -- ************************************************************************
     -- 5.2.1.1.1.1

--     telcoTempThresholdsIndex OBJECT-TYPE
--             		      SYNTAX  INTEGER
--                   	      ACCESS  read-only
--                 	      STATUS  mandatory
--                 	      DESCRIPTION
--                 	      "BladeCenter T Temperature Thresholds index.
--                              
--                              NOTE: This MIB is for BladeCenter T only." 
--                	      ::= { telcoTempThresholdsEntry 1 }

     -- ************************************************************************
     -- BladeCenter T Temperature Threshold Entry - Name
     -- ************************************************************************
     -- 5.2.1.1.1.2
                         
--     telcoTempThresholdsName  OBJECT-TYPE
--                	      SYNTAX  OCTET STRING
--                 	      ACCESS  read-only
--                 	      STATUS  mandatory
--                 	      DESCRIPTION
--                              "BladeCenter T Temperature Threshold Name. The values 
--                              and meanings are as follows:
--                                MM  : Management Module Temperature
--                                SYS : System Temperature
--                                
--                              NOTE: This MIB is for BladeCenter T only." 
--                              ::= { telcoTempThresholdsEntry 2 }


     -- ************************************************************************
     -- BladeCenter T Temperature Threshold Entry - Low Critical
     -- ************************************************************************
     -- 5.2.1.1.1.3
     
--     telcoTempThresholdsLCRT  OBJECT-TYPE
--                 	      SYNTAX  OCTET STRING
--                              ACCESS  read-only
--                 	      STATUS  mandatory
--                 	      DESCRIPTION
--                	      "BladeCenter T Temperature Low Critical Threshold value.
--                              An octet string expressed as 'sddd.dd Centigrade' where:
--                                  s is the sign ('-' for negative or '+' for positive)
--                                  d is a decimal digit or blank space for a leading zero.
--                              The string 'Not Readable!' or 'Not Writeable' indicates
--                              that the given monitor is not supported on this system.
--                              
--                              NOTE: This MIB is for BladeCenter T only." 
--                              ::= { telcoTempThresholdsEntry 3 }
--
     -- ************************************************************************
     -- BladeCenter T Temperature Threshold Entry - Low Critical Reset
     -- ************************************************************************
     -- 5.2.1.1.1.4
--
--     telcoTempThresholdsLCRTH OBJECT-TYPE
--                 	      SYNTAX  OCTET STRING
--                              ACCESS  read-only
--                 	      STATUS  mandatory
--                 	      DESCRIPTION
--                	      "BladeCenter T Temperature Low Critical Reset (Hysteresis) Threshold value.
--                              An octet string expressed as 'sddd.dd Centigrade' where:
--                                  s is the sign ('-' for negative or '+' for positive)
--                                  d is a decimal digit or blank space for a leading zero.
--                              The string 'Not Readable!' or 'Not Writeable' indicates
--                              that the given monitor is not supported on this system.
--                              
--                              NOTE: This MIB is for BladeCenter T only." 
--                              ::= { telcoTempThresholdsEntry 4 }
--
--
     -- ************************************************************************
     -- BladeCenter T Temperature Threshold Entry - Low Major
     -- ************************************************************************
     -- 5.2.1.1.1.5
--
--     telcoTempThresholdsLMJR  OBJECT-TYPE
--                 	      SYNTAX  OCTET STRING
--                              ACCESS  read-only
--                 	      STATUS  mandatory
--                 	      DESCRIPTION
--                	      "BladeCenter T Temperature Low Major Threshold value.
--                              An octet string expressed as 'sddd.dd Centigrade' where:
--                                  s is the sign ('-' for negative or '+' for positive)
--                                  d is a decimal digit or blank space for a leading zero.
--                              The string 'Not Readable!' or 'Not Writeable' indicates
--                              that the given monitor is not supported on this system.
--                              
--                              NOTE: This MIB is for BladeCenter T only." 
--                              ::= { telcoTempThresholdsEntry 5 }


     -- ************************************************************************
     -- BladeCenter T Temperature Threshold Entry - Low Major Reset
     -- ************************************************************************
     -- 5.2.1.1.1.6

--     telcoTempThresholdsLMJRH OBJECT-TYPE
--                 	      SYNTAX  OCTET STRING
--                              ACCESS  read-only
--                 	      STATUS  mandatory
--                 	      DESCRIPTION
--                	      "BladeCenter T Temperature Low Major Reset (Hysteresis) Threshold value.
--                              An octet string expressed as 'sddd.dd Centigrade' where:
--                                  s is the sign ('-' for negative or '+' for positive)
--                                  d is a decimal digit or blank space for a leading zero.
--                              The string 'Not Readable!' or 'Not Writeable' indicates
--                              that the given monitor is not supported on this system.
--                              
--                              NOTE: This MIB is for BladeCenter T only." 
--                              ::= { telcoTempThresholdsEntry 6 }
--                              

     -- ************************************************************************
     -- BladeCenter T Temperature Threshold Entry - Low Minor 
     -- ************************************************************************
     -- 5.2.1.1.1.7

--     telcoTempThresholdsLMNR  OBJECT-TYPE
--                 	      SYNTAX  OCTET STRING
--                              ACCESS  read-only
--                 	      STATUS  mandatory
--                 	      DESCRIPTION
--                	      "BladeCenter T Temperature Low Minor Threshold value.
--                              An octet string expressed as 'sddd.dd Centigrade' where:
--                                  s is the sign ('-' for negative or '+' for positive)
--                                  d is a decimal digit or blank space for a leading zero.
--                              The string 'Not Readable!' or 'Not Writeable' indicates
--                              that the given monitor is not supported on this system.
--                              
--                              NOTE: This MIB is for BladeCenter T only." 
--                              ::= { telcoTempThresholdsEntry 7 }
--                              

     -- ************************************************************************
     -- BladeCenter T Temperature Threshold Entry - Low Minor Reset
     -- ************************************************************************
     -- 5.2.1.1.1.8

--     telcoTempThresholdsLMNRH OBJECT-TYPE
--                 	      SYNTAX  OCTET STRING
--                              ACCESS  read-only
--                 	      STATUS  mandatory
--                 	      DESCRIPTION
--                	      "BladeCenter T Temperature Low Minor Reset (Hysteresis) Threshold value.
--                              An octet string expressed as 'sddd.dd Centigrade' where:
--                                  s is the sign ('-' for negative or '+' for positive)
--                                  d is a decimal digit or blank space for a leading zero.
--                              The string 'Not Readable!' or 'Not Writeable' indicates
--                              that the given monitor is not supported on this system.
--                              
--                              NOTE: This MIB is for BladeCenter T only." 
--                              ::= { telcoTempThresholdsEntry 8 }
--

     -- ************************************************************************
     -- BladeCenter T Temperature Threshold Entry - High Minor Reset
     -- ************************************************************************
     -- 5.2.1.1.1.9
     
--     telcoTempThresholdsHMNRH OBJECT-TYPE
--                 	      SYNTAX  OCTET STRING
--                              ACCESS  read-only
--                 	      STATUS  mandatory
--                 	      DESCRIPTION
--                	      "BladeCenter T Temperature High Minor Reset (Hysteresis) Threshold value.
--                              An octet string expressed as 'sddd.dd Centigrade' where:
--                                  s is the sign ('-' for negative or '+' for positive)
--                                  d is a decimal digit or blank space for a leading zero.
--                              The string 'Not Readable!' or 'Not Writeable' indicates
--                              that the given monitor is not supported on this system.
--                              
--                              NOTE: This MIB is for BladeCenter T only." 
--                              ::= { telcoTempThresholdsEntry 9 }

     -- ************************************************************************
     -- BladeCenter T Temperature Threshold Entry - High Minor
     -- ************************************************************************
     -- 5.2.1.1.1.10
     
--     telcoTempThresholdsHMNR  OBJECT-TYPE
--                 	      SYNTAX  OCTET STRING
--                              ACCESS  read-only
--                 	      STATUS  mandatory
--                 	      DESCRIPTION
--                	      "BladeCenter T Temperature High Minor Threshold value.
--                              An octet string expressed as 'sddd.dd Centigrade' where:
--                                  s is the sign ('-' for negative or '+' for positive)
--                                  d is a decimal digit or blank space for a leading zero.
--                              The string 'Not Readable!' or 'Not Writeable' indicates
--                              that the given monitor is not supported on this system.
--                              
--                              NOTE: This MIB is for BladeCenter T only." 
--                              ::= { telcoTempThresholdsEntry 10 }
--

     -- ************************************************************************
     -- BladeCenter T Temperature Threshold Entry - High Major Reset
     -- ************************************************************************
     -- 5.2.1.1.1.11

--     telcoTempThresholdsHMJRH OBJECT-TYPE
--                 	      SYNTAX  OCTET STRING
--                              ACCESS  read-only
--                 	      STATUS  mandatory
--                 	      DESCRIPTION
--                	      "BladeCenter T Temperature High Major Reset (Hysteresis) Threshold value.
--                              An octet string expressed as 'sddd.dd Centigrade' where:
--                                  s is the sign ('-' for negative or '+' for positive)
--                                  d is a decimal digit or blank space for a leading zero.
--                              The string 'Not Readable!' or 'Not Writeable' indicates
--                              that the given monitor is not supported on this system.
--                              
--                              NOTE: This MIB is for BladeCenter T only." 
--                              ::= { telcoTempThresholdsEntry 11 }
--

     -- ************************************************************************
     -- BladeCenter T Temperature Threshold Entry - High Major 
     -- ************************************************************************
     -- 5.2.1.1.1.12

--     telcoTempThresholdsHMJR  OBJECT-TYPE
--                 	      SYNTAX  OCTET STRING
--                              ACCESS  read-only
--                 	      STATUS  mandatory
--                 	      DESCRIPTION
--                	      "BladeCenter T Temperature High Major Threshold value.
--                              An octet string expressed as 'sddd.dd Centigrade' where:
--                                  s is the sign ('-' for negative or '+' for positive)
--                                  d is a decimal digit or blank space for a leading zero.
--                              The string 'Not Readable!' or 'Not Writeable' indicates
--                              that the given monitor is not supported on this system.
--                              
--                              NOTE: This MIB is for BladeCenter T only." 
--                              ::= { telcoTempThresholdsEntry 12 }
                              

     -- ************************************************************************
     -- BladeCenter T Temperature Threshold Entry - High Critical Reset
     -- ************************************************************************
     -- 5.2.1.1.1.13

--     telcoTempThresholdsHCRTH OBJECT-TYPE
--                 	      SYNTAX  OCTET STRING
--                              ACCESS  read-only
--                 	      STATUS  mandatory
--                 	      DESCRIPTION
--                	      "BladeCenter T Temperature High Critical Reset (Hysteresis) Threshold value.
--                              An octet string expressed as 'sddd.dd Centigrade' where:
--                                  s is the sign ('-' for negative or '+' for positive)
--                                  d is a decimal digit or blank space for a leading zero.
--                              The string 'Not Readable!' or 'Not Writeable' indicates
--                              that the given monitor is not supported on this system.
                              
--                              NOTE: This MIB is for BladeCenter T only." 
--                              ::= { telcoTempThresholdsEntry 13 }
                              

     -- ************************************************************************
     -- BladeCenter T Temperature Threshold Entry - High Critical
     -- ************************************************************************
     -- 5.2.1.1.1.14

--     telcoTempThresholdsHCRT  OBJECT-TYPE
--                 	      SYNTAX  OCTET STRING
--                              ACCESS  read-only
--                 	      STATUS  mandatory
--                 	      DESCRIPTION
--                	      "BladeCenter T Temperature High Critical Threshold value.
--                              An octet string expressed as 'sddd.dd Centigrade' where:
--                                  s is the sign ('-' for negative or '+' for positive)
--                                  d is a decimal digit or blank space for a leading zero.
--                              The string 'Not Readable!' or 'Not Writeable' indicates
--                              that the given monitor is not supported on this system.
                              
--                              NOTE: This MIB is for BladeCenter T only." 
--                              ::= { telcoTempThresholdsEntry 14 }
                              
     -- ************************************************************************
     -- BladeCenter T Temperature Threshold Entry - Default Value
     -- ************************************************************************
     -- 5.2.1.1.1.15

--     telcoTempThresholdsDFT   OBJECT-TYPE
--                 	      SYNTAX  OCTET STRING
--                              ACCESS  read-only
--                 	      STATUS  mandatory
--                 	      DESCRIPTION
--                	      "BladeCenter T Temperature Default Threshold value. The settings
--                               are for the following components:
--                                MM  : Management Module Temperature
--                                
--                              NOTE: This MIB is for BladeCenter T only." 
--                              ::= { telcoTempThresholdsEntry 15 }

     -- ************************************************************************
     -- BladeCenter T Temperature Threshold Entry - Lower Hysteresis 
     -- ************************************************************************
     -- 5.2.1.1.1.16

--     telcoTempThresholdsLHyst   OBJECT-TYPE
--                 	      SYNTAX  OCTET STRING
--                              ACCESS  read-only
--                 	      STATUS  mandatory
--                 	      DESCRIPTION
--                	      "BladeCenter T Temperature Lower Hysteresis value. 
--                              An octet string expressed as 'sddd.dd Centigrade' where:
--                                  s is the sign ('-' for negative or '+' for positive)
--                                  d is a decimal digit or blank space for a leading zero.
--                              
--                              NOTE: This MIB is for BladeCenter T only." 
--                              ::= { telcoTempThresholdsEntry 16 }

     -- ************************************************************************
     -- BladeCenter T Temperature Threshold Entry - Upper Hysteresis 
     -- ************************************************************************
     -- 5.2.1.1.1.17

--     telcoTempThresholdsHHyst   OBJECT-TYPE
--                 	      SYNTAX  OCTET STRING
--                              ACCESS  read-only
--                 	      STATUS  mandatory
--                 	      DESCRIPTION
--                	      "BladeCenter T Temperature Upper Hysteresis value. 
--                              An octet string expressed as 'sddd.dd Centigrade' where:
--                                  s is the sign ('-' for negative or '+' for positive)
--                                  d is a decimal digit or blank space for a leading zero.
--                              
--                                
--                              NOTE: This MIB is for BladeCenter T only." 
--                              ::= { telcoTempThresholdsEntry 17 }
--

     -- ************************************************************************
     -- BladeCenter T Voltage Threshold 
     -- ************************************************************************
     -- 5.2.2
 
--     telcoVoltageThresholds   OBJECT IDENTIFIER ::= { telcoThresholds 2 }
     

     -- ************************************************************************
     -- BladeCenter T Voltage Threshold Table
     -- ***********************************************************************
     -- 5.2.2.1

--     telcoVoltageThresholdsTable OBJECT-TYPE
--                   		 SYNTAX  SEQUENCE OF TelcoVoltageThresholdsEntry
--                  	         ACCESS  not-accessible
--                   		 STATUS  mandatory
--                  		 DESCRIPTION
--                   		 "Table of Voltage Threshold summary.
--                                  
--                                 NOTE: This MIB is for BladeCenter T only." 
--                   		 ::= { telcoVoltageThresholds 1 }
     -- ************************************************************************
     -- BladeCenter T Voltage Threshold Entry
     -- ************************************************************************
     -- 5.2.2.1.1                            

--     telcoVoltageThresholdsEntry OBJECT-TYPE
--                   		 SYNTAX TelcoVoltageThresholdsEntry
--                  		 ACCESS  not-accessible
--            		         STATUS  mandatory
--                   		 DESCRIPTION
--            		         "BladeCenter T Voltage Thresholds entry
--                                 
--                                 NOTE: This MIB is for BladeCenter T only." 
--                  		 INDEX { telcoVoltageThresholdsIndex }
--                   		 ::= { telcoVoltageThresholdsTable 1 }

     -- ************************************************************************
     -- BladeCenter T Voltage Threshold Entry Sequence
     -- ************************************************************************
     
--     TelcoVoltageThresholdsEntry ::= SEQUENCE {
--                 		 telcoVoltageThresholdsIndex INTEGER,
--                                 telcoVoltageThresholdsName  OCTET STRING, 
--                 		 telcoVoltageThresholdsLCRT  OCTET STRING,
--	 		         telcoVoltageThresholdsLCRTH OCTET STRING,
--			         telcoVoltageThresholdsLMJR  OCTET STRING,
--		        	 telcoVoltageThresholdsLMJRH OCTET STRING,
-- 			         telcoVoltageThresholdsLMNR  OCTET STRING,
--	 		         telcoVoltageThresholdsLMNRH OCTET STRING,
--			         telcoVoltageThresholdsHMNRH OCTET STRING,
--			         telcoVoltageThresholdsHMNR  OCTET STRING,
--			         telcoVoltageThresholdsHMJRH OCTET STRING,
--	 		         telcoVoltageThresholdsHMJR  OCTET STRING,
--			         telcoVoltageThresholdsHCRTH OCTET STRING,
--			         telcoVoltageThresholdsHCRT  OCTET STRING,
--                                 telcoVoltageThresholdsDFT   OCTET STRING,
--                                 telcoVoltageThresholdsLHyst OCTET STRING,
--                                 telcoVoltageThresholdsHHyst OCTET STRING
--                                 }

     -- ************************************************************************
     -- BladeCenter T Voltage Threshold Entry - Index
     -- ************************************************************************
     -- 5.2.2.1.1.1

--     telcoVoltageThresholdsIndex OBJECT-TYPE
--             		         SYNTAX  INTEGER
--                   		 ACCESS  read-only
--                 		 STATUS  mandatory
--                 		 DESCRIPTION
--                 		 "BladeCenter T Voltage Thresholds index.
--                                 
--                                 NOTE: This MIB is for BladeCenter T only." 
--                		 ::= { telcoVoltageThresholdsEntry 1 }
                                 
     -- ************************************************************************
     -- BladeCenter T Voltage Threshold Entry - Name
     -- ************************************************************************
     -- 5.2.2.1.1.2
     
--     telcoVoltageThresholdsName  OBJECT-TYPE
--                		 SYNTAX  OCTET STRING
--                 		 ACCESS  read-only
--                 		 STATUS  mandatory
--                 		 DESCRIPTION
--                 		 "BladeCenter T Voltage Threshold Name. The values 
--                                 and meanings are as follows:
--                                   Plus 5 Volts   : +5 Volt power supply voltage
--                                   Plus 3.3 Volts : +3.3 Volt power supply voltage
--                                   Plus 12 Volts  : +12 Volt power supply voltage
--                                   Minus 5 Volts  : -5 Volt power supply voltage
--                                   Plus 2.5 Volts : +2.5 Volt power supply voltage
--                                   Plus 1.8 Volts : +1.8 Volt power supply voltage
--                                   
--                                 NOTE: This MIB is for BladeCenter T only." 
--                                 ::= { telcoVoltageThresholdsEntry 2 }
                                 
     -- ************************************************************************
     -- BladeCenter T Voltage Threshold Entry - Low Critical
     -- ************************************************************************
     -- 5.2.2.1.1.3

--     telcoVoltageThresholdsLCRT  OBJECT-TYPE
--                 	         SYNTAX  OCTET STRING
--                                 ACCESS  read-only
--                 		 STATUS  mandatory
--                 		 DESCRIPTION
--                                 "BladeCenter T Voltage Low Critical Threshold value.
--                                 An octet string expressed as 'sdd.dd Volts' where:
--                                   s is the sign ('-' for negative or '+' for positive)
--                                   d is a decimal digit or blank space for a leading zero.
--                                 The string 'Not Readable!' or 'Not Writeable' indicates
--                                 that the given monitor is not supported on this system.
--                                 
--                                 NOTE: This MIB is for BladeCenter T only." 
--                 		 ::= { telcoVoltageThresholdsEntry 3 }

     -- ************************************************************************
     -- BladeCenter T Voltage Threshold Entry - Low Critical Reset
     -- ************************************************************************
     -- 5.2.2.1.1.4
     
--     telcoVoltageThresholdsLCRTH OBJECT-TYPE
--                 	         SYNTAX  OCTET STRING
--                                 ACCESS  read-only
--                 		 STATUS  mandatory
--                 		 DESCRIPTION
--                		 "BladeCenter T Voltage Low Critical Reset (Hysteresis) Threshold value.
--                                 An octet string expressed as 'sdd.dd Volts' where:
--                                   s is the sign ('-' for negative or '+' for positive)
--                                   d is a decimal digit or blank space for a leading zero.
--                                 The string 'Not Readable!' or 'Not Writeable' indicates
--                                 that the given monitor is not supported on this system.
--                                 
--                                 NOTE: This MIB is for BladeCenter T only." 
--                                 ::= { telcoVoltageThresholdsEntry 4 }
                                
     -- ************************************************************************
     -- BladeCenter T Voltage Threshold Entry - Low Major
     -- ************************************************************************
     -- 5.2.2.1.1.5

--     telcoVoltageThresholdsLMJR  OBJECT-TYPE
--                 	         SYNTAX  OCTET STRING
--                                 ACCESS  read-only
--                 		 STATUS  mandatory
--                 		 DESCRIPTION
--                		 "BladeCenter T Voltage Low Major Threshold value.
--                                 An octet string expressed as 'sdd.dd Volts' where:
--                                   s is the sign ('-' for negative or '+' for positive)
--                                   d is a decimal digit or blank space for a leading zero.
--                                 The string 'Not Readable!' or 'Not Writeable' indicates
--                                 that the given monitor is not supported on this system.
--                                 
--                                 NOTE: This MIB is for BladeCenter T only." 
--                 		 ::= { telcoVoltageThresholdsEntry 5 }

     -- ************************************************************************
     -- BladeCenter T Voltage Threshold Entry - Low Major Reset
     -- ************************************************************************
     -- 5.2.2.1.1.6
 
--     telcoVoltageThresholdsLMJRH OBJECT-TYPE
--                 	 	 SYNTAX  OCTET STRING
--                                 ACCESS  read-only
--                 		 STATUS  mandatory
--                 		 DESCRIPTION
--                		 "BladeCenter T Voltage Low Major Reset (Hysteresis) Threshold value.
--                                 An octet string expressed as 'sdd.dd Volts' where:
--                                   s is the sign ('-' for negative or '+' for positive)
--                                   d is a decimal digit or blank space for a leading zero.
--                                 The string 'Not Readable!' or 'Not Writeable' indicates
--                                 that the given monitor is not supported on this system.
--                                 
--                                 NOTE: This MIB is for BladeCenter T only." 
--                 		 ::= { telcoVoltageThresholdsEntry 6 }

     -- ************************************************************************
     -- BladeCenter T Voltage Threshold Entry - Low Minor
     -- ************************************************************************
     -- 5.2.2.1.1.7

--     telcoVoltageThresholdsLMNR  OBJECT-TYPE
--                 		 SYNTAX  OCTET STRING
--                                 ACCESS  read-only
--                 		 STATUS  mandatory
--                 		 DESCRIPTION
--                		 "BladeCenter T Voltage Low Minor Threshold value.
--                                 An octet string expressed as 'sdd.dd Volts' where:
--                                   s is the sign ('-' for negative or '+' for positive)
--                                   d is a decimal digit or blank space for a leading zero.
--                                 The string 'Not Readable!' or 'Not Writeable' indicates
--                                 that the given monitor is not supported on this system.
--                                 
--                                 NOTE: This MIB is for BladeCenter T only." 
--                 		 ::= { telcoVoltageThresholdsEntry 7 }

     -- ************************************************************************
     -- BladeCenter T Voltage Threshold Entry - Low Minor Reset
     -- ************************************************************************
     -- 5.2.2.1.1.8

--     telcoVoltageThresholdsLMNRH OBJECT-TYPE
--                 		 SYNTAX  OCTET STRING
--                                 ACCESS  read-only
--                 		 STATUS  mandatory
--                 		 DESCRIPTION
--                		 "BladeCenter T Voltage Low Minor Reset (Hysteresis) Threshold value.
--                                 An octet string expressed as 'sdd.dd Volts' where:
--                                   s is the sign ('-' for negative or '+' for positive)
--                                   d is a decimal digit or blank space for a leading zero.
--                                 The string 'Not Readable!' or 'Not Writeable' indicates
--                                 that the given monitor is not supported on this system.
--                                 
--                                 NOTE: This MIB is for BladeCenter T only." 
--                 		 ::= { telcoVoltageThresholdsEntry 8 }
                                
     -- ************************************************************************
     -- BladeCenter T Voltage Threshold Entry - High Minor Reset
     -- ************************************************************************
     -- 5.2.2.1.1.9

--     telcoVoltageThresholdsHMNRH OBJECT-TYPE
--                 	         SYNTAX  OCTET STRING
--                                 ACCESS  read-only
--                 		 STATUS  mandatory
--                 		 DESCRIPTION
--                		 "BladeCenter T Voltage High Minor Reset Threshold value.
--                                 An octet string expressed as 'sdd.dd Volts' where:
--                                   s is the sign ('-' for negative or '+' for positive)
--                                   d is a decimal digit or blank space for a leading zero.
--                                 The string 'Not Readable!' or 'Not Writeable' indicates
--                                 that the given monitor is not supported on this system.
--                                 
--                                 NOTE: This MIB is for BladeCenter T only." 
--                 		 ::= { telcoVoltageThresholdsEntry 9 }

     -- ************************************************************************
     -- BladeCenter T Voltage Threshold Entry - High Minor 
     -- ************************************************************************
     -- 5.2.2.1.1.10

--     telcoVoltageThresholdsHMNR  OBJECT-TYPE
--                 		 SYNTAX  OCTET STRING
--                                 ACCESS  read-only
--                 		 STATUS  mandatory
--                 		 DESCRIPTION
--                		 "BladeCenter T Voltage High Minor Threshold value.
--                                 An octet string expressed as 'sdd.dd Volts' where:
--                                   s is the sign ('-' for negative or '+' for positive)
--                                   d is a decimal digit or blank space for a leading zero.
--                                 The string 'Not Readable!' or 'Not Writeable' indicates
--                                 that the given monitor is not supported on this system.
--                                 
--                                 NOTE: This MIB is for BladeCenter T only." 
--                 		 ::= { telcoVoltageThresholdsEntry 10 }

     -- ************************************************************************
     -- BladeCenter T Voltage Threshold Entry - High Major Reset 
     -- ************************************************************************
     -- 5.2.2.1.1.11

--     telcoVoltageThresholdsHMJRH OBJECT-TYPE
--                 		 SYNTAX  OCTET STRING
--                                 ACCESS  read-only
--                 		 STATUS  mandatory
--                 		 DESCRIPTION
--                		 "BladeCenter T Voltage High Major Reset (Hysteresis) Threshold value.
--                                 An octet string expressed as 'sdd.dd Volts' where:
--                                   s is the sign ('-' for negative or '+' for positive)
--                                   d is a decimal digit or blank space for a leading zero.
--                                 The string 'Not Readable!' or 'Not Writeable' indicates
--                                 that the given monitor is not supported on this system.
--                                 
--                                 NOTE: This MIB is for BladeCenter T only." 
--                 		 ::= { telcoVoltageThresholdsEntry 11 }


     -- ************************************************************************
     -- BladeCenter T Voltage Threshold Entry - High Major 
     -- ************************************************************************
     -- 5.2.2.1.1.12

--     telcoVoltageThresholdsHMJR  OBJECT-TYPE
--                 		 SYNTAX  OCTET STRING
--                                 ACCESS  read-only
--                 		 STATUS  mandatory
--                 		 DESCRIPTION
--                		 "BladeCenter T Voltage High Major Threshold value.
--                                 An octet string expressed as 'sdd.dd Volts' where:
--                                   s is the sign ('-' for negative or '+' for positive)
--                                   d is a decimal digit or blank space for a leading zero.
--                                 The string 'Not Readable!' or 'Not Writeable' indicates
--                                 that the given monitor is not supported on this system.
--                                 
--                                 NOTE: This MIB is for BladeCenter T only." 
--                 		 ::= { telcoVoltageThresholdsEntry 12 }

     -- ************************************************************************
     -- BladeCenter T Voltage Threshold Entry - High Critical Reset 
     -- ************************************************************************
     -- 5.2.2.1.1.13
   
--     telcoVoltageThresholdsHCRTH OBJECT-TYPE
--                 		 SYNTAX  OCTET STRING
--                                 ACCESS  read-only
--                 		 STATUS  mandatory
--                 		 DESCRIPTION
--                		 "BladeCenter T Voltage High Critical Reset (Hysteresis) Threshold value.
--                                 An octet string expressed as 'sdd.dd Volts' where:
--                                   s is the sign ('-' for negative or '+' for positive)
--                                   d is a decimal digit or blank space for a leading zero.
--                                 The string 'Not Readable!' or 'Not Writeable' indicates
--                                 that the given monitor is not supported on this system.
--                                 
--                                 NOTE: This MIB is for BladeCenter T only." 
--                 		 ::= { telcoVoltageThresholdsEntry 13 }

     -- ************************************************************************
     -- BladeCenter T Voltage Threshold Entry - High Critical 
     -- ************************************************************************
     -- 5.2.2.1.1.14

--     telcoVoltageThresholdsHCRT  OBJECT-TYPE
--                 		 SYNTAX  OCTET STRING
--                                 ACCESS  read-only
--                 		 STATUS  mandatory
--                 		 DESCRIPTION
--                		 "BladeCenter T Voltage High Critical Threshold value.
--                                 An octet string expressed as 'sdd.dd Volts' where:
--                                   s is the sign ('-' for negative or '+' for positive)
--                                   d is a decimal digit or blank space for a leading zero.
--                                 The string 'Not Readable!' or 'Not Writeable' indicates
--                                 that the given monitor is not supported on this system.
--                                 
--                                 NOTE: This MIB is for BladeCenter T only." 
--                 		 ::= { telcoVoltageThresholdsEntry 14 }

     -- ************************************************************************
     -- BladeCenter T Voltage Threshold Entry - Default 
     -- ************************************************************************
     -- 5.2.2.1.1.15

--     telcoVoltageThresholdsDFT   OBJECT-TYPE
--                 		 SYNTAX  OCTET STRING
--                                 ACCESS  read-only
--                 		 STATUS  mandatory
--                 		 DESCRIPTION
--                		 "BladeCenter T Voltage Default Threshold value. The settings
--                                  are for the following components:
--                                   Plus 5 Volts   : +5 Volt power supply voltage
--                                   Plus 3.3 Volts : +3.3 Volt power supply voltage
--                                   Plus 12 Volts  : +12 Volt power supply voltage
--                                   Minus 5 Volts  : -5 Volt power supply voltage
--                                   Plus 2.5 Volts : +2.5 Volt power supply voltage
--                                   Plus 1.8 Volts : +1.8 Volt power supply voltage
--                                   
--                                 NOTE: This MIB is for BladeCenter T only." 
--                                 ::= { telcoVoltageThresholdsEntry 15 }

     -- ************************************************************************
     -- BladeCenter T Voltage Threshold Entry - Lower Hysteresis 
     -- ************************************************************************
     -- 5.2.2.1.1.16

--     telcoVoltageThresholdsLHyst   OBJECT-TYPE
--                 		 SYNTAX  OCTET STRING
--                                 ACCESS  read-only
--                 		 STATUS  mandatory
--                 		 DESCRIPTION
--                		 "BladeCenter T Voltage Lower Hysteresis value. 
--                                 An octet string expressed as 'sdd.dd Volts' where:
--                                   s is the sign ('-' for negative or '+' for positive)
--                                   d is a decimal digit or blank space for a leading zero.
--                                   
--                                 NOTE: This MIB is for BladeCenter T only." 
--                                 ::= { telcoVoltageThresholdsEntry 16 }

     -- ************************************************************************
     -- BladeCenter T Voltage Threshold Entry - Upper Hysteresis 
     -- ************************************************************************
     -- 5.2.2.1.1.17

--     telcoVoltageThresholdsHHyst   OBJECT-TYPE
--                 		 SYNTAX  OCTET STRING
--                                 ACCESS  read-only
--                 		 STATUS  mandatory
--                 		 DESCRIPTION
--                		 "BladeCenter T Voltage Upper Hysteresis value. 
--                                 An octet string expressed as 'sdd.dd Volts' where:
--                                   s is the sign ('-' for negative or '+' for positive)
--                                   d is a decimal digit or blank space for a leading zero.
--                                   
--                                 NOTE: This MIB is for BladeCenter T only." 
--                                 ::= { telcoVoltageThresholdsEntry 17 }

     -- ************************************************************************
     -- BladeCenter T OEM grouping
     -- ************************************************************************
     -- 5.127
    
     telcoOEM OBJECT IDENTIFIER ::= { telcoManagement 127 }
     
     telcoOEMs                   OBJECT-TYPE
                 		 SYNTAX  OCTET STRING
                    		 ACCESS  read-only
                 		 STATUS  mandatory
                 		 DESCRIPTION
                                 "A bitmap of information about the contents of this subtree. The 
                                 bitmap is a variable length string containing a list of 1's and 0's.
                                 Every bit that is set to 1 has a corresponding subtree entry that
                                 is supported in firmware, while a 0 means that the subtree entry
                                 is unavailable."
                                 ::= { telcoOEM 1 }

     
  -- *********************************************************************************
  --  System Services
  --  ********************************************************************************
      -- ********************************************************************************
      -- System Watch Dog Timers 
      -- currently not supported in cdttable
      -- ********************************************************************************
      -- 5.1
--    serverTimers OBJECT IDENTIFIER ::= { generalSystemSettings 1 }
--
       -- 5.1.1
--     serverPost   OBJECT-TYPE
--                  SYNTAX  INTEGER {
--                    disabled(0),
--                    threeAndHalfMinutes(7),
--                    fourMinutes(8),
--                    fourAndHalfMinutes(9),
--                    fiveMinutes(10),
--                    sevenAndHalfMinutes(15),
--                    tenMinutes(20),
--                    fifteenMinutes(30),
--                    twentyMinutes(40),
--                    thirtyMinutes(60),
--                    oneHour(120),
--                    twoHours(240)
--                   }
--                   ACCESS  read-write
--                   STATUS  mandatory
--                   DESCRIPTION
--                   "Number in 30 second intervals the MM will wait
--                   for the server to complete power on self test (POST).
--                   If the system fails to complete
--                   POST within this time, the MM will generate a
--                   POST timeout alert (if enabled) and automatically restart the system
--                   one time.  Once the system is restarted, the POST
--                   watchdog is automatically disabled until the operating system is
--                   shutdown and the server is power cycled."
--                   ::= { serverTimers 1 }
--
       -- 5.1.2
--     oSHang       OBJECT-TYPE
--                  SYNTAX  INTEGER {
--                    disabled(0),
--                    twoAndHalfMinutes(150),
--                    threeMinutes(180),
--                    threeAndHalfMinutes(210),
--                    fourMinutes(240)
--                   }
--                   ACCESS  read-write
--                   STATUS  mandatory
--                   DESCRIPTION
--                   "Number, in 1 second intervals, the MM will
--                   check to insure the OS is operating properly.
--                   If the operating system fails to respond within 6 seconds to one
--                   of these checks, the remote supervisor adapter will generate
--                   an O/S Timeout alert (if enabled) and automatically restart the
--                   system one time.  Once the system is restarted, the O/S Watchdog
--                   is automatically disabled until the operating
--                   system is shutdown and the server is power cycled."
--                   ::= { serverTimers 2 }
--
       -- 5.1.3
--     oSLoader     OBJECT-TYPE
--                  SYNTAX  INTEGER {
--                    disabled(0),
--                    oneHalfMinutes(1),
--                    oneMinutes(2),
--                    oneAndHalfMinutes(3),
--                    twoMinutes(4),
--                    twoAndHalfMinutes(5),
--                    threeMinutes(6),
--                    fourMinutes(8),
--                    fourAndHalfMinutes(9),
--                    fiveMinutes(10),
--                    fiveAndHalfMinutes(11),
--                    sevenAndHalfMinutes(15),
--                    tenMinutes(20),
--                    fifteenMinutes(30),
--                    twentyMinutes(40),
--                    thirtyMinutes(60),
--                    oneHour(120),
--                    twoHours(240)
--                   }
--                   ACCESS  read-write
--                   STATUS  mandatory
--                   DESCRIPTION
--                   "Number in 30 second intervals the remote MM will wait
--                   between completion of POST and the end of loading the OS.
--                   If this interval is exceeded, the MM will
--                   generate a Loader Timeout alert (if enabled) and automatically restart
--                   the system one time.  Once the system is restarted, the
--                   Loader Timeout is automatically disabled until the operating
--                   system is shutdown and the server is power cycled."
--                   ::= { serverTimers 3 }
--

  -- 
  --  System Power Control
  -- 

      -- ********************************************************************************
      -- System Power off control
      -- ********************************************************************************
      -- 6.3
--    powerOffSystemControl OBJECT IDENTIFIER ::= { systemPower 3 }
--
       -- 6.3.2
--     powerOffImmediately  OBJECT-TYPE
--                   SYNTAX  INTEGER {
--                    execute(1)
--                   }
--                   ACCESS   write-only
--                   STATUS  mandatory
--                   DESCRIPTION
--                   "Power off the system immediately."
--                   ::= { powerOffSystemControl 2 }
--
      -- ********************************************************************************
      -- System Power on control
      -- ********************************************************************************
      -- 6.4
--    powerOnSystemControl OBJECT IDENTIFIER ::= { systemPower 4 }
--
       -- 6.4.2
--     powerOnImmediately  OBJECT-TYPE
--                   SYNTAX  INTEGER {
--                    execute(1)
--                   }
--                   ACCESS  write-only
--                   STATUS  mandatory
--                   DESCRIPTION
--                   "Power on the system immediately."
--                   ::= { powerOnSystemControl 2 }
--

  --  ********************************************************************************
  --  Restart Control
  --  ********************************************************************************

      -- 7.2
--    restartSystemImmediately  OBJECT-TYPE
--                   SYNTAX  INTEGER {
--                    execute(1)
--                   }
--                   ACCESS  write-only
--                   STATUS  mandatory
--                   DESCRIPTION
--                   "Restart the system immediately and then the boot OS."
--                   ::= { restartReset 2 }
--

      -- 7.4
      restartSPImmediately   OBJECT-TYPE
                     SYNTAX  INTEGER {
                      execute(1)
                     }
                     ACCESS  read-write
                     STATUS  mandatory
                     DESCRIPTION
                     "Restart the MM immediately.
                     
                     NOTE: Value returned for the GET command is meaningless for 
                     this MIB."
                     ::= { restartReset 4 }

      -- 7.7
      switchOverRedundantMM  OBJECT-TYPE
                     SYNTAX  INTEGER {
                      execute(1)
                     }
                     ACCESS  read-write
                     STATUS  mandatory
                     DESCRIPTION
                     "Switch over to the redundant Management Module.
                     
                     NOTE: Value returned for the GET command is meaningless for 
                     this MIB."
                     ::= { restartReset 7 }

      -- 2.5.3 + 7.4???
      resetSPConfigAndRestart  OBJECT-TYPE
                    SYNTAX  INTEGER {
                      execute(1)
                     }
                    ACCESS  read-write
                    STATUS  mandatory
                    DESCRIPTION
                    "Will cause all the MM information to be reset to it's
                    initial factory defaults (all previous configuration
                    information is lost) and the MM will be re-started.
                    
                    NOTE: Value returned for the GET command is meaningless 
                    for this MIB."
                    ::= { restartReset 20 }

  --  ********************************************************************************
  --  processorBlade
  --  ********************************************************************************
    --This group of objects provides information specific to blades
    -- 22.1
    processorBlade OBJECT IDENTIFIER ::= { bladeCenter 1 }

      -- ********************************************************************************
      -- Media and I/O
      -- ********************************************************************************
      -- 22.1.1
      bladeMediaTrayBladeId  OBJECT-TYPE
                     SYNTAX  INTEGER {
                       managementModule(0),
                       blade1(1),
                       blade2(2),
                       blade3(3),
                       blade4(4),
                       blade5(5),
                       blade6(6),
                       blade7(7),
                       blade8(8),
                       blade9(9),
                       blade10(10),
                       blade11(11),
                       blade12(12),
                       blade13(13),
                       blade14(14)
                     }
                     ACCESS  read-write
                     STATUS  mandatory
                     DESCRIPTION
                     "Allocate the media tray to a blade of a BladeCenter system.
                     On a get command, a blade ID of 0x00 means that no blade is
                     currently using the device.  A set command cannot allocate
                     the media tray to the management module."
                     ::= { processorBlade 1 }

      -- 22.1.2
      bladeKVMBladeId  OBJECT-TYPE
                     SYNTAX  INTEGER {
                       managementModule(0),
                       blade1(1),
                       blade2(2),
                       blade3(3),
                       blade4(4),
                       blade5(5),
                       blade6(6),
                       blade7(7),
                       blade8(8),
                       blade9(9),
                       blade10(10),
                       blade11(11),
                       blade12(12),
                       blade13(13),
                       blade14(14)
                     }
                     ACCESS  read-write
                     STATUS  mandatory
                     DESCRIPTION
                     "Allocate the keyboard, video, and mouse ports (KVM) to a blade
                     of a blade runner system.  On a get command, a blade ID of 0x00
                     means that no blade is currently using the devices.  A set
                     command cannot allocate the KVM to the management module."
                     ::= { processorBlade 2 }

      -- ********************************************************************************
      -- Blade boot sequence
      -- ********************************************************************************
      -- 22.1.3
      bladeBootSequenceTable OBJECT-TYPE
                     SYNTAX  SEQUENCE OF BladeBootSequenceEntry
                     ACCESS  not-accessible
                     STATUS  mandatory
                     DESCRIPTION
                     "Table of blade boot sequence information.  Contains
                     the boot sequence information for each blade."
                     ::= { processorBlade 3 }

       bladeBootSequenceEntry OBJECT-TYPE
                     SYNTAX BladeBootSequenceEntry
                     ACCESS  not-accessible
                     STATUS  mandatory
                     DESCRIPTION
                     "Boot sequence entry"
                     INDEX { bootSequenceIndex }
                     ::= { bladeBootSequenceTable 1 }


       BladeBootSequenceEntry ::= SEQUENCE {
                   bootSequenceIndex INTEGER,
                   bootSequenceBladeId INTEGER,
                   bootSequenceBladeExists INTEGER,
                   bootSequenceBladePowerState INTEGER,
                   bootSequenceBladeHealthState INTEGER,
                   bootSequenceBladeName OCTET STRING,
                   bootSequence1 INTEGER,
                   bootSequence2 INTEGER,
                   bootSequence3 INTEGER,
                   bootSequence4 INTEGER
       }

       bootSequenceIndex  OBJECT-TYPE
                   SYNTAX  INTEGER
                   ACCESS  read-only
                   STATUS  mandatory
                   DESCRIPTION
                   "Blade boot sequence index."
                   ::= { bladeBootSequenceEntry 1 }

       bootSequenceBladeId   OBJECT-TYPE
                   SYNTAX  INTEGER {
--                        managementModule(0),
                       blade1(1),
                       blade2(2),
                       blade3(3),
                       blade4(4),
                       blade5(5),
                       blade6(6),
                       blade7(7),
                       blade8(8),
                       blade9(9),
                       blade10(10),
                       blade11(11),
                       blade12(12),
                       blade13(13),
                       blade14(14)
                     }
                   ACCESS  read-only
                   STATUS  mandatory
                   DESCRIPTION
                   "The numeric blade ID."
                   ::= { bladeBootSequenceEntry 2 }

       bootSequenceBladeExists OBJECT-TYPE
                   SYNTAX  INTEGER {
                     false(0),
                     true(1)
                   }
                   ACCESS  read-only
                   STATUS  mandatory
                   DESCRIPTION
                   "Indicates whether the server blade specified exists or not."
                   ::= { bladeBootSequenceEntry 3 }

       bootSequenceBladePowerState OBJECT-TYPE
                   SYNTAX  INTEGER {
                     off(0),
                     on(1)
                   }
                   ACCESS  read-only
                   STATUS  mandatory
                   DESCRIPTION
                   "Indicates whether the server blade specified is powered on or not."
                   ::= { bladeBootSequenceEntry 4 }

       bootSequenceBladeHealthState  OBJECT-TYPE
                 SYNTAX  INTEGER {
                   unknown(0),
                   good(1),
                   warning(2),
                   bad(3)
                 }
                 ACCESS  read-only
                 STATUS  mandatory
                 DESCRIPTION
                 "The system health state for the blade server.
                 1 = good, 2 = warning, 3 = bad."
                 ::= { bladeBootSequenceEntry 5 }

       bootSequenceBladeName OBJECT-TYPE
                   SYNTAX  OCTET STRING
                   ACCESS  read-only
                   STATUS  mandatory
                   DESCRIPTION
                   "The name of the blade as a null terminated string."
                   ::= { bladeBootSequenceEntry 6 }

       bootSequence1 OBJECT-TYPE
                   SYNTAX  INTEGER {
                     noneSpecified(0),
                     floppy(1),
                     cdrom(2),
                     hardDrive0(3),
                     hardDrive1(4),
                     hardDrive2(5),
                     hardDrive3(6),
                     networkBoot(7),
                     iscsi(8),
                     iscsiCritical(9),
                     hardDrive4(10),
                     notAvailable(255)
                   }
                   ACCESS  read-write
                   STATUS  mandatory
                   DESCRIPTION
                   "The boot device for this blade boot sequence. Note that some types
                   of blades don't support floppy disk drive. It is recommended that all
                   boot sequence 1,2 3, and 4 be configured starting from boot sequence 1.
                   If there is any duplication of the configured boot sequence and the 
                   current configuration, the two boot sequence will be swapped. 
                   For an example: the current boot sequence is
                        1=HD0, 2=CD, 3=FD, 4=HD1
                   If the user wants to configure 1=FD which is a duplication of 3 then the
                   new boot sequence will be:
                        1=FD, 2=CD, 3=HD0, 4=HD1  (1 and 3 swapped)
                   Not all hard drives are available on all blade configurations.
                   The 'Iscsi critical' option has a special meaning: the blade tries to 
                   find an iscsi boot device and if it does not it keeps trying forever."
                   ::= { bladeBootSequenceEntry 7 }

       bootSequence2 OBJECT-TYPE
                   SYNTAX  INTEGER {
                     noneSpecified(0),
                     floppy(1),
                     cdrom(2),
                     hardDrive0(3),
                     hardDrive1(4),
                     hardDrive2(5),
                     hardDrive3(6),
                     networkBoot(7),
                     iscsi(8),
                     iscsiCritical(9),
                     hardDrive4(10),
                     notAvailable(255)
                   }
                   ACCESS  read-write
                   STATUS  mandatory
                   DESCRIPTION
                   "The boot device for this blade boot sequence. Note that some types
                   of blades don't support floppy disk drive. It is recommended that all
                   boot sequence 1,2 3, and 4 be configured starting from boot sequence 1.
                   If there is any duplication of the configured boot sequence and the 
                   current configuration, the two boot sequence will be swapped. 
                   For an example: the current boot sequence is
                        1=HD0, 2=CD, 3=FD, 4=HD1
                   If the user wants to configure 1=FD which is a duplication of 3 then the
                   new boot sequence will be:
                        1=FD, 2=CD, 3=HD0, 4=HD1  (1 and 3 swapped)
                   Not all hard drives are available on all blade configurations.
                   The 'Iscsi critical' option has a special meaning: the blade tries to 
                   find an iscsi boot device and if it does not it keeps trying forever."
                   ::= { bladeBootSequenceEntry 8 }

       bootSequence3 OBJECT-TYPE
                   SYNTAX  INTEGER {
                     noneSpecified(0),
                     floppy(1),
                     cdrom(2),
                     hardDrive0(3),
                     hardDrive1(4),
                     hardDrive2(5),
                     hardDrive3(6),
                     networkBoot(7),
                     iscsi(8),
                     iscsiCritical(9),
                     hardDrive4(10),
                     notAvailable(255)
                   }
                   ACCESS  read-write
                   STATUS  mandatory
                   DESCRIPTION
                   "The boot device for this blade boot sequence. Note that some types
                   of blades don't support floppy disk drive. It is recommended that all
                   boot sequence 1,2 3, and 4 be configured starting from boot sequence 1.
                   If there is any duplication of the configured boot sequence and the 
                   current configuration, the two boot sequence will be swapped. 
                   For an example: the current boot sequence is
                        1=HD0, 2=CD, 3=FD, 4=HD1
                   If the user wants to configure 1=FD which is a duplication of 3 then the
                   new boot sequence will be:
                        1=FD, 2=CD, 3=HD0, 4=HD1  (1 and 3 swapped)
                   Not all hard drives are available on all blade configurations.
                   The 'Iscsi critical' option has a special meaning: the blade tries to 
                   find an iscsi boot device and if it does not it keeps trying forever."
                   ::= { bladeBootSequenceEntry 9 }

       bootSequence4 OBJECT-TYPE
                   SYNTAX  INTEGER {
                     noneSpecified(0),
                     floppy(1),
                     cdrom(2),
                     hardDrive0(3),
                     hardDrive1(4),
                     hardDrive2(5),
                     hardDrive3(6),
                     networkBoot(7),
                     iscsi(8),
                     iscsiCritical(9),
                     hardDrive4(10),
                     notAvailable(255)
                   }
                   ACCESS  read-write
                   STATUS  mandatory
                   DESCRIPTION
                   "The boot device for this blade boot sequence. Note that some types
                   of blades don't support floppy disk drive. It is recommended that all
                   boot sequence 1,2 3, and 4 be configured starting from boot sequence 1.
                   If there is any duplication of the configured boot sequence and the 
                   current configuration, the two boot sequence will be swapped. 
                   For an example: the current boot sequence is
                        1=HD0, 2=CD, 3=FD, 4=HD1
                   If the user wants to configure 1=FD which is a duplication of 3 then the
                   new boot sequence will be:
                        1=FD, 2=CD, 3=HD0, 4=HD1  (1 and 3 swapped)
                   Not all hard drives are available on all blade configurations.
                   The 'Iscsi critical' option has a special meaning: the blade tries to 
                   find an iscsi boot device and if it does not it keeps trying forever."
                   ::= { bladeBootSequenceEntry 10 }

      -- ********************************************************************************
      -- Blade local control
      -- ********************************************************************************
      -- 22.1.4
      bladeRemoteControl OBJECT IDENTIFIER ::= { processorBlade 4 }
       -- remote blade control

        bladeRemoteControlTable OBJECT-TYPE
                       SYNTAX  SEQUENCE OF BladeRemoteControlEntry
                       ACCESS  not-accessible
                       STATUS  mandatory
                       DESCRIPTION
                       "Table of blade remote power control information.
                       Contains power on/off enablement status for each blade."
                       ::= { bladeRemoteControl 1 }

         bladeRemoteControlEntry OBJECT-TYPE
                       SYNTAX BladeRemoteControlEntry
                       ACCESS  not-accessible
                       STATUS  mandatory
                       DESCRIPTION
                       "Remote power control entry"
                       INDEX { remoteControlIndex }
                       ::= { bladeRemoteControlTable 1 }


         BladeRemoteControlEntry ::= SEQUENCE {
                     remoteControlIndex INTEGER,
                     remoteControlBladeId INTEGER,
                     remoteControlBladeExists INTEGER,
                     remoteControlBladePowerState INTEGER,
                     remoteControlBladeHealthState INTEGER,
                     remoteControlBladeName OCTET STRING,
                     remotePowerControlEnable INTEGER,
                     remoteMediaTrayControlEnable INTEGER,
                     remoteKVMControlEnable INTEGER,
                     remoteWakeOnLanControlEnable INTEGER
         }

         remoteControlIndex  OBJECT-TYPE
                     SYNTAX  INTEGER
                     ACCESS  read-only
                     STATUS  mandatory
                     DESCRIPTION
                     "Blade remote power control index."
                     ::= { bladeRemoteControlEntry 1 }


         remoteControlBladeId  OBJECT-TYPE
                     SYNTAX  INTEGER {
--                        managementModule(0),
                       blade1(1),
                       blade2(2),
                       blade3(3),
                       blade4(4),
                       blade5(5),
                       blade6(6),
                       blade7(7),
                       blade8(8),
                       blade9(9),
                       blade10(10),
                       blade11(11),
                       blade12(12),
                       blade13(13),
                       blade14(14)
                     }
                     ACCESS  read-only
                     STATUS  mandatory
                     DESCRIPTION
                     "The numeric blade ID."
                     ::= { bladeRemoteControlEntry 2 }

         remoteControlBladeExists OBJECT-TYPE
                     SYNTAX  INTEGER {
                       false(0),
                       true(1)
                     }
                     ACCESS  read-only
                     STATUS  mandatory
                     DESCRIPTION
                     "Indicates whether the server blade specified exists or not."
                     ::= { bladeRemoteControlEntry 3 }

         remoteControlBladePowerState OBJECT-TYPE
                     SYNTAX  INTEGER {
                       off(0),
                       on(1),
                       unknown(255)
                     }
                     ACCESS  read-only
                     STATUS  mandatory
                     DESCRIPTION
                     "The power state for blade server.
                      0 = off, 1 = on, 255 = unknown."
                     ::= { bladeRemoteControlEntry 4 }

         remoteControlBladeHealthState  OBJECT-TYPE
                   SYNTAX  INTEGER {
                     unknown(0),
                     good(1),
                     warning(2),
                     bad(3),
                     kernel(4),
                     init(5)
                   }
                   ACCESS  read-only
                   STATUS  mandatory
                   DESCRIPTION
                   "The system health state for the blade server.
                   0 = unknown, 1 = good, 2 = warning, 3 = bad, 4 = kernel mode, 5 = discovering"
                   ::= { bladeRemoteControlEntry 5 }

         remoteControlBladeName OBJECT-TYPE
                     SYNTAX  OCTET STRING
                     ACCESS  read-only
                     STATUS  mandatory
                     DESCRIPTION
                     "The name of the blade as a null terminated string."
                     ::= { bladeRemoteControlEntry 6 }

         -- 22.1.4.1
         remotePowerControlEnable OBJECT-TYPE
                     SYNTAX  INTEGER {
                       disabled(0),
                       enabled(1)
                     }
                     ACCESS  read-write
                     STATUS  mandatory
                     DESCRIPTION
                     "Blade remote power control enablement status."
                     ::= { bladeRemoteControlEntry 7 }

         -- 22.1.4.2
         remoteMediaTrayControlEnable OBJECT-TYPE
                     SYNTAX  INTEGER {
                       disabled(0),
                       enabled(1)
                     }
                     ACCESS  read-write
                     STATUS  mandatory
                     DESCRIPTION
                     "Blade media tray enablement status."
                     ::= { bladeRemoteControlEntry 8 }


         -- 22.1.4.3
         remoteKVMControlEnable OBJECT-TYPE
                     SYNTAX  INTEGER {
                       disabled(0),
                       enabled(1)
                     }
                     ACCESS  read-write
                     STATUS  mandatory
                     DESCRIPTION
                     "Blade KVM enablement status. Note that some types of blades
                     don't support KVM"
                     ::= { bladeRemoteControlEntry 9 }

         -- 22.1.4.4
         remoteWakeOnLanControlEnable OBJECT-TYPE
                     SYNTAX  INTEGER {
                       disabled(0),
                       enabled(1)
                     }
                     ACCESS  read-write
                     STATUS  mandatory
                     DESCRIPTION
                     "Blade Wake On Lan enablement status."
                     ::= { bladeRemoteControlEntry 10 }


       bladePolicy  OBJECT IDENTIFIER ::= { bladeRemoteControl 2}
       -- global blade remote control policy

         -- 22.1.4.1
         bladePolicyPowerControlEnable OBJECT-TYPE
                     SYNTAX  INTEGER {
                       disabled(0),
                       enabled(1)
                     }
                     ACCESS  read-write
                     STATUS  mandatory
                     DESCRIPTION
                     "Blade remote power control enablement status policy.
                     
                     NOTE: Value returned for the GET command is meaningless
                     for this MIB."
                     ::= { bladePolicy 1 }

         -- 22.1.4.2
         bladePolicyMediaTrayControlEnable OBJECT-TYPE
                     SYNTAX  INTEGER {
                       disabled(0),
                       enabled(1)
                     }
                     ACCESS  read-write
                     STATUS  mandatory
                     DESCRIPTION
                     "Blade media tray enablement status policy.
                     
                     NOTE: Value returned for the GET command is meaningless 
                     for this MIB."
                     ::= { bladePolicy 2 }


         -- 22.1.4.3
         bladePolicyKVMControlEnable OBJECT-TYPE
                     SYNTAX  INTEGER {
                       disabled(0),
                       enabled(1)
                     }
                     ACCESS  read-write
                     STATUS  mandatory
                     DESCRIPTION
                     "Blade KVM enablement status policy. Note that some types of blades
                     don't support KVM.  
                     
                     NOTE: Value returned for the GET command is meaningless for 
                     this MIB."
                     ::= { bladePolicy 3 }

         -- 22.1.4.4
         bladePolicyWakeOnLanControlEnable OBJECT-TYPE
                     SYNTAX  INTEGER {
                       disabled(0),
                       enabled(1)
                     }
                     ACCESS  read-write
                     STATUS  mandatory
                     DESCRIPTION
                     "Blade Wake On Lan enablement status policy.
                     
                     NOTE: Value returned for the GET command is meaningless 
                     for this MIB."
                     ::= { bladePolicy 4 }


      -- ********************************************************************************
      -- Blade system health state params
      -- ********************************************************************************


      -- 22.1.5  
      -- rename this to blade health?
      bladeMonitors OBJECT IDENTIFIER ::= { processorBlade 5 }

       -- 22.1.5.1
       bladeSystemStatusTable OBJECT-TYPE
                     SYNTAX  SEQUENCE OF BladeSystemStatusEntry
                     ACCESS  not-accessible
                     STATUS  mandatory
                     DESCRIPTION
                     "Table of blade status information."
                     ::= { bladeMonitors 1 }

       bladeSystemStatusEntry OBJECT-TYPE
                     SYNTAX BladeSystemStatusEntry
                     ACCESS  not-accessible
                     STATUS  mandatory
                     DESCRIPTION
                     "Blade system status entry"
                     INDEX { bladeStatusIndex }
                     ::= { bladeSystemStatusTable 1 }


       BladeSystemStatusEntry ::= SEQUENCE {
                   bladeStatusIndex INTEGER,
                   bladeId INTEGER,
                   bladeExists INTEGER,
                   bladePowerState INTEGER,
                   bladeHealthState INTEGER,
                   bladeName OCTET STRING,
                   bladeRemotePowerEnable INTEGER,
                   bladeRemoteMediaTrayEnable INTEGER,
                   bladeRemoteKVMEnable INTEGER,
                   bladeConnectionType INTEGER,
                   bladeOwnsKVM INTEGER,
                   bladeOwnsMediaTray INTEGER,
                   bladeRemoteWakeOnLanEnable INTEGER,
                   bladeServerExpansion INTEGER,
                   bladeWidth INTEGER,
                   bladeSupportCapacityOnDemand INTEGER
       }


       bladeStatusIndex OBJECT-TYPE
                   SYNTAX  INTEGER
                   ACCESS  read-only
                   STATUS  mandatory
                   DESCRIPTION
                   "Blade system status index."
                   ::= { bladeSystemStatusEntry 1 }

       bladeId OBJECT-TYPE
                   SYNTAX  INTEGER {
--                        managementModule(0),
                       blade1(1),
                       blade2(2),
                       blade3(3),
                       blade4(4),
                       blade5(5),
                       blade6(6),
                       blade7(7),
                       blade8(8),
                       blade9(9),
                       blade10(10),
                       blade11(11),
                       blade12(12),
                       blade13(13),
                       blade14(14)
                     }
                   ACCESS  read-only
                   STATUS  mandatory
                   DESCRIPTION
                   "The numeric blade ID."
                   ::= { bladeSystemStatusEntry 2 }

       bladeExists OBJECT-TYPE
                   SYNTAX  INTEGER {
                     false(0),
                     true(1)
                   }
                   ACCESS  read-only
                   STATUS  mandatory
                   DESCRIPTION
                   "Indicates whether the server blade specified exists or not."
                   ::= { bladeSystemStatusEntry 3 }

       bladePowerState  OBJECT-TYPE
                   SYNTAX  INTEGER {
                     off(0),
                     on(1)
                   }
                   ACCESS  read-only
                   STATUS  mandatory
                   DESCRIPTION
                   "Indicates whether the server blade specified is powered on or not."
                   ::= { bladeSystemStatusEntry 4 }

       bladeHealthState  OBJECT-TYPE
                   SYNTAX  INTEGER {
                     unknown(0),
                     good(1),
                     warning(2),
                     bad(3)
                   }
                   ACCESS  read-only
                   STATUS  mandatory
                   DESCRIPTION
                   "The system health state for the blade server.
                   0 = unknown, 1 = good, 2 = warning, 3 = bad."
                   ::= { bladeSystemStatusEntry 5 }

       bladeName OBJECT-TYPE
                   SYNTAX  OCTET STRING
                   ACCESS  read-only
                   STATUS  mandatory
                   DESCRIPTION
                   "The name of the blade as a null terminated string."
                   ::= { bladeSystemStatusEntry 6 }

       bladeRemotePowerEnable  OBJECT-TYPE
                   SYNTAX  INTEGER {
                     disabled(0),
                     enabled(1)
                   }
                   ACCESS  read-only
                   STATUS  mandatory
                   DESCRIPTION
                   "Remote power state for the blade server.
                   0x01 indicates enabled."
                   ::= { bladeSystemStatusEntry 7 }

       bladeRemoteMediaTrayEnable  OBJECT-TYPE
                   SYNTAX  INTEGER {
                     disabled(0),
                     enabled(1)
                   }
                   ACCESS  read-only
                   STATUS  mandatory
                   DESCRIPTION
                   "Remote Media Tray state for the blade server.
                   0x01 indicates enabled."
                   ::= { bladeSystemStatusEntry 8 }

       bladeRemoteKVMEnable  OBJECT-TYPE
                   SYNTAX  INTEGER {
                     disabled(0),
                     enabled(1)
                   }
                   ACCESS  read-only
                   STATUS  mandatory
                   DESCRIPTION
                   "Remote keyboard/video/monitor state for the blade server.
                   0x01 indicates enabled. Note that some types of blades
                     don't support KVM"
                   ::= { bladeSystemStatusEntry 9 }

       bladeConnectionType  OBJECT-TYPE
                   SYNTAX  INTEGER {
                     none(0),
                     ethernet(1),
                     fiber(2)
                   }
                   ACCESS  read-only
                   STATUS  mandatory
                   DESCRIPTION
                   "Connection type for the blade server.
                   0 = none, 1 = ethernet, 2 = fiber"
                   ::= { bladeSystemStatusEntry 10 }

       bladeOwnsKVM  OBJECT-TYPE
                   SYNTAX  INTEGER {
                     false(0),
                     true(1)
                   }
                   ACCESS  read-only
                   STATUS  mandatory
                   DESCRIPTION
                   "Indicates whether the MM owns the KVM.
                   0 = false, 1 = true. Note that some types of blades
                     don't support KVM"
                   ::= { bladeSystemStatusEntry 11 }

       bladeOwnsMediaTray  OBJECT-TYPE
                   SYNTAX  INTEGER {
                     false(0),
                     true(1)
                   }
                   ACCESS  read-only
                   STATUS  mandatory
                   DESCRIPTION
                   "Indicates whether the blade owns the Media Tray.
                   0 = false, 1 = true."
                   ::= { bladeSystemStatusEntry 12 }

       bladeRemoteWakeOnLanEnable  OBJECT-TYPE
                   SYNTAX  INTEGER {
                     disabled(0),
                     enabled(1)
                   }
                   ACCESS  read-only
                   STATUS  mandatory
                   DESCRIPTION
                   "Remote wake on LAN state for the blade server.
                   0x01 indicates enabled."
                   ::= { bladeSystemStatusEntry 13 }

       bladeServerExpansion  OBJECT-TYPE
                   SYNTAX  INTEGER {
                     no(0),
                     yes(1)
                   }
                   ACCESS  read-only
                   STATUS  mandatory
                   DESCRIPTION
                   "This shows whether this blade server has a blade server expansion attached. 
                   A yes column indicates that a blade storage expansion is installed for this 
                   blade server."
                   ::= { bladeSystemStatusEntry 14 }

       bladeWidth  OBJECT-TYPE
                   SYNTAX  INTEGER
                   ACCESS  read-only
                   STATUS  mandatory
                   DESCRIPTION
                   "The width of the blade including any supplement blade attached to it" 
                   ::= { bladeSystemStatusEntry 15 }

       bladeSupportCapacityOnDemand  OBJECT-TYPE
                   SYNTAX  INTEGER {
                     no(0),
                     yes(1)
                   }
                   ACCESS  read-only
                   STATUS  mandatory
                   DESCRIPTION
                   "This shows whether this blade server support Capacity On Demand." 
                   ::= { bladeSystemStatusEntry 16 }

      -- 22.1.5.2
      bladeHealthSummaryTable OBJECT-TYPE
                    SYNTAX  SEQUENCE OF BladeHealthSummaryEntry
                    ACCESS  not-accessible
                    STATUS  mandatory
                    DESCRIPTION
                    "Table of blade health summary information.
                    Contains information about the overall blade health status."
                    ::= { bladeMonitors 2 }

      bladeHealthSummaryEntry OBJECT-TYPE
                    SYNTAX BladeHealthSummaryEntry
                    ACCESS  not-accessible
                    STATUS  mandatory
                    DESCRIPTION
                    "Blade health summary entry"
                    INDEX { bladeHealthSummaryIndex }
                    ::= { bladeHealthSummaryTable 1 }


      BladeHealthSummaryEntry ::= SEQUENCE {
                  bladeHealthSummaryIndex INTEGER,
                  bladeHealthSummaryBladeId INTEGER,
                  bladeHealthSummarySeverity OCTET STRING,
                  bladeHealthSummaryDescription OCTET STRING
      }


      bladeHealthSummaryIndex  OBJECT-TYPE
                  SYNTAX  INTEGER
                  ACCESS  read-only
                  STATUS  mandatory
                  DESCRIPTION
                  "Blade health summary index."
                  ::= { bladeHealthSummaryEntry 1 }

       bladeHealthSummaryBladeId OBJECT-TYPE
                   SYNTAX  INTEGER {
                       blade1(1),
                       blade2(2),
                       blade3(3),
                       blade4(4),
                       blade5(5),
                       blade6(6),
                       blade7(7),
                       blade8(8),
                       blade9(9),
                       blade10(10),
                       blade11(11),
                       blade12(12),
                       blade13(13),
                       blade14(14)
                     }
                   ACCESS  read-only
                   STATUS  mandatory
                   DESCRIPTION
                   "The numeric blade ID."
                   ::= { bladeHealthSummaryEntry 2 }

      bladeHealthSummarySeverity  OBJECT-TYPE
                  SYNTAX  OCTET STRING
                  ACCESS  read-only
                  STATUS  mandatory
                  DESCRIPTION
                  "System health summary severity."
                  ::= { bladeHealthSummaryEntry 3 }

      bladeHealthSummaryDescription  OBJECT-TYPE
                  SYNTAX  OCTET STRING
                  ACCESS  read-only
                  STATUS  mandatory
                  DESCRIPTION
                  "System health summary description."
                  ::= { bladeHealthSummaryEntry 4 }



      bladeTemperaturesTable OBJECT-TYPE
                     SYNTAX  SEQUENCE OF BladeTemperaturesEntry
                     ACCESS  not-accessible
                     STATUS  mandatory
                     DESCRIPTION
                     "Table of blade temperatures information."
                     ::= { bladeMonitors 3 }

       bladeTemperaturesEntry OBJECT-TYPE
                     SYNTAX BladeTemperaturesEntry
                     ACCESS  not-accessible
                     STATUS  mandatory
                     DESCRIPTION
                     "Blade temperatures table entry"
                     INDEX { temperatureIndex }
                     ::= { bladeTemperaturesTable 1 }


       BladeTemperaturesEntry ::= SEQUENCE {
                   temperatureIndex INTEGER,
                   temperatureBladeId INTEGER,
                   temperatureBladeExists INTEGER,
                   temperatureBladePowerState INTEGER,
                   temperatureBladeName OCTET STRING,
                   temperatureCPU1 OCTET STRING,
                   temperatureCPU2 OCTET STRING,
                   temperatureCPU3 OCTET STRING,
                   temperatureCPU4 OCTET STRING,
                   temperatureDASD1 OCTET STRING,
                   bladeSensorTempCapability INTEGER,
                   bladeSensor1Temp OCTET STRING,
                   bladeSensor2Temp OCTET STRING,
                   bladeSensor3Temp OCTET STRING,
                   bladeSensor4Temp OCTET STRING,
                   bladeSensor5Temp OCTET STRING,
                   bladeSensor6Temp OCTET STRING

       }

       temperatureIndex  OBJECT-TYPE
                   SYNTAX  INTEGER
                   ACCESS  read-only
                   STATUS  mandatory
                   DESCRIPTION
                   "Blade temperatures table index."
                   ::= { bladeTemperaturesEntry 1 }


       temperatureBladeId  OBJECT-TYPE
                   SYNTAX  INTEGER {
--                      managementModule(0),
                     blade1(1),
                     blade2(2),
                     blade3(3),
                     blade4(4),
                     blade5(5),
                     blade6(6),
                     blade7(7),
                     blade8(8),
                     blade9(9),
                     blade10(10),
                     blade11(11),
                     blade12(12),
                     blade13(13),
                     blade14(14)
                   }
                   ACCESS  read-only
                   STATUS  mandatory
                   DESCRIPTION
                   "The numeric blade ID."
                   ::= { bladeTemperaturesEntry 2 }

       temperatureBladeExists OBJECT-TYPE
                   SYNTAX  INTEGER {
                     false(0),
                     true(1)
                   }
                   ACCESS  read-only
                   STATUS  mandatory
                   DESCRIPTION
                   "Indicates whether the server blade specified exists or not."
                   ::= { bladeTemperaturesEntry 3 }

       temperatureBladePowerState OBJECT-TYPE
                   SYNTAX  INTEGER {
                     off(0),
                     on(1)
                   }
                   ACCESS  read-only
                   STATUS  mandatory
                   DESCRIPTION
                   "Indicates whether the server blade specified is powered on or not."
                   ::= { bladeTemperaturesEntry 4 }

       temperatureBladeName OBJECT-TYPE
                   SYNTAX  OCTET STRING
                   ACCESS  read-only
                   STATUS  mandatory
                   DESCRIPTION
                   "The name of the blade as a null terminated string."
                   ::= { bladeTemperaturesEntry 5 }

       temperatureCPU1 OBJECT-TYPE
                   SYNTAX  OCTET STRING
                   ACCESS  read-only
                   STATUS  mandatory
                   DESCRIPTION
                   "The blade CPU temperature in degrees centigrade(C).
                   An octet string expressed as 'sddd.dd Centigrade' where:
                   s is the sign ('-' for negative or blank space for positive)
                   d is a decimal digit or blank space for leading zeroes.
                   The string 'Not Readable!' indicates that the given monitor
                   is not supported on this system.
                   The string 'No Temperature' indicates that the given monitor
                   does not exist on this system or is powered off."
                   ::= { bladeTemperaturesEntry 6 }

       temperatureCPU2 OBJECT-TYPE
                   SYNTAX  OCTET STRING
                   ACCESS  read-only
                   STATUS  mandatory
                   DESCRIPTION
                   "The blade CPU temperature in degrees centigrade(C).
                   An octet string expressed as 'sddd.dd Centigrade' where:
                   s is the sign ('-' for negative or blank space for positive)
                   d is a decimal digit or blank space for leading zeroes.
                   The string 'Not Readable!' indicates that the given monitor
                   is not supported on this system.
                   The string 'No Temperature' indicates that the given monitor
                   does not exist on this system or is powered off."
                   ::= { bladeTemperaturesEntry 7 }

       temperatureCPU3 OBJECT-TYPE
                   SYNTAX  OCTET STRING
                   ACCESS  read-only
                   STATUS  mandatory
                   DESCRIPTION
                   "The blade CPU temperature in degrees centigrade(C).
                   An octet string expressed as 'sddd.dd Centigrade' where:
                   s is the sign ('-' for negative or blank space for positive)
                   d is a decimal digit or blank space for leading zeroes.
                   The string 'Not Readable!' indicates that the given monitor
                   is not supported on this system.
                   The string 'No Temperature' indicates that the given monitor
                   does not exist on this system or is powered off."
                   ::= { bladeTemperaturesEntry 8 }

       temperatureCPU4 OBJECT-TYPE
                   SYNTAX  OCTET STRING
                   ACCESS  read-only
                   STATUS  mandatory
                   DESCRIPTION
                   "The blade CPU temperature in degrees centigrade(C).
                   An octet string expressed as 'sddd.dd Centigrade' where:
                   s is the sign ('-' for negative or blank space for positive)
                   d is a decimal digit or blank space for leading zeroes.
                   The string 'Not Readable!' indicates that the given monitor
                   is not supported on this system.
                   The string 'No Temperature' indicates that the given monitor
                   does not exist on this system or is powered off."
                   ::= { bladeTemperaturesEntry 9 }

       temperatureDASD1 OBJECT-TYPE
                   SYNTAX  OCTET STRING
                   ACCESS  read-only
                   STATUS  mandatory
                   DESCRIPTION
                   "The blade DASD temperature in degrees centigrade(C).
                   An octet string expressed as 'sddd.dd Centigrade' where:
                   s is the sign ('-' for negative or blank space for positive)
                   d is a decimal digit or blank space for leading zeroes.
                   The string 'Not Readable!' indicates that the given monitor
                   is not supported on this system.
                   The string 'No Temperature' indicates that the given monitor
                   does not exist on this system or is powered off."
                   ::= { bladeTemperaturesEntry 10 }
                   
       bladeSensorTempCapability OBJECT-TYPE
                   SYNTAX  INTEGER {
                     false(0),
                     true(1)
                   }
                   ACCESS  read-only
                   STATUS  mandatory
                   DESCRIPTION
                   "Indicates whether the server blade is IPMI capable or not."
                   ::= { bladeTemperaturesEntry 11 }                   
                   
       bladeSensor1Temp OBJECT-TYPE
                   SYNTAX  OCTET STRING
                   ACCESS  read-only
                   STATUS  mandatory
                   DESCRIPTION
                   "Temperature reading for an IPMI blade expressed in degrees centigrade(C).
                   An octet string expressed as 'sddd.dd Centigrade' where:
                   s is the sign ('-' for negative or blank space for positive)
                   d is a decimal digit or blank space for leading zeroes.
                   The string 'Not Readable!' indicates that the given monitor
                   is not supported on this system.
                   The string 'No Temperature' indicates that the given monitor
                   does not exist on this system or is powered off."
                   ::= { bladeTemperaturesEntry 12 }

       bladeSensor2Temp OBJECT-TYPE
                   SYNTAX  OCTET STRING
                   ACCESS  read-only
                   STATUS  mandatory
                   DESCRIPTION
                   "Temperature reading for an IPMI blade expressed in degrees centigrade(C).
                   An octet string expressed as 'sddd.dd Centigrade' where:
                   s is the sign ('-' for negative or blank space for positive)
                   d is a decimal digit or blank space for leading zeroes.
                   The string 'Not Readable!' indicates that the given monitor
                   is not supported on this system.
                   The string 'No Temperature' indicates that the given monitor
                   does not exist on this system or is powered off."
                   ::= { bladeTemperaturesEntry 13 }

       bladeSensor3Temp OBJECT-TYPE
                   SYNTAX  OCTET STRING
                   ACCESS  read-only
                   STATUS  mandatory
                   DESCRIPTION
                   "Temperature reading for an IPMI blade expressed in degrees centigrade(C).
                   An octet string expressed as 'sddd.dd Centigrade' where:
                   s is the sign ('-' for negative or blank space for positive)
                   d is a decimal digit or blank space for leading zeroes.
                   The string 'Not Readable!' indicates that the given monitor
                   is not supported on this system.
                   The string 'No Temperature' indicates that the given monitor
                   does not exist on this system or is powered off."
                   ::= { bladeTemperaturesEntry 14 }

       bladeSensor4Temp OBJECT-TYPE
                   SYNTAX  OCTET STRING
                   ACCESS  read-only
                   STATUS  mandatory
                   DESCRIPTION
                   "Temperature reading for an IPMI blade expressed in degrees centigrade(C).
                   An octet string expressed as 'sddd.dd Centigrade' where:
                   s is the sign ('-' for negative or blank space for positive)
                   d is a decimal digit or blank space for leading zeroes.
                   The string 'Not Readable!' indicates that the given monitor
                   is not supported on this system.
                   The string 'No Temperature' indicates that the given monitor
                   does not exist on this system or is powered off."
                   ::= { bladeTemperaturesEntry 15 }

       bladeSensor5Temp OBJECT-TYPE
                   SYNTAX  OCTET STRING
                   ACCESS  read-only
                   STATUS  mandatory
                   DESCRIPTION
                   "Temperature reading for an IPMI blade expressed in degrees centigrade(C).
                   An octet string expressed as 'sddd.dd Centigrade' where:
                   s is the sign ('-' for negative or blank space for positive)
                   d is a decimal digit or blank space for leading zeroes.
                   The string 'Not Readable!' indicates that the given monitor
                   is not supported on this system.
                   The string 'No Temperature' indicates that the given monitor
                   does not exist on this system or is powered off."
                   ::= { bladeTemperaturesEntry 16 }

       bladeSensor6Temp OBJECT-TYPE
                   SYNTAX  OCTET STRING
                   ACCESS  read-only
                   STATUS  mandatory
                   DESCRIPTION
                   "Temperature reading for an IPMI blade expressed in degrees centigrade(C).
                   An octet string expressed as 'sddd.dd Centigrade' where:
                   s is the sign ('-' for negative or blank space for positive)
                   d is a decimal digit or blank space for leading zeroes.
                   The string 'Not Readable!' indicates that the given monitor
                   is not supported on this system.
                   The string 'No Temperature' indicates that the given monitor
                   does not exist on this system or is powered off."
                   ::= { bladeTemperaturesEntry 17 }

      bladeTemperatureThresholdsTable OBJECT-TYPE
                     SYNTAX  SEQUENCE OF BladeTemperatureThresholdsEntry
                     ACCESS  not-accessible
                     STATUS  mandatory
                     DESCRIPTION
                     "Table of blade temperature thresholds information."
                     ::= { bladeMonitors 4 }

       bladeTemperatureThresholdsEntry OBJECT-TYPE
                     SYNTAX BladeTemperatureThresholdsEntry
                     ACCESS  not-accessible
                     STATUS  mandatory
                     DESCRIPTION
                     "Blade temperature thresholds table entry"
                     INDEX { temperatureThresholdIndex }
                     ::= { bladeTemperatureThresholdsTable 1 }


       BladeTemperatureThresholdsEntry ::= SEQUENCE {
                   temperatureThresholdIndex INTEGER,
                   temperatureThresholdBladeId INTEGER,
                   temperatureThresholdBladeExists INTEGER,
                   temperatureThresholdBladePowerState INTEGER,
                   temperatureThresholdBladeName OCTET STRING,
                   temperatureCPU1HardShutdown OCTET STRING,
                   temperatureCPU1Warning OCTET STRING,
                   temperatureCPU1WarningReset OCTET STRING,
                   temperatureCPU2HardShutdown OCTET STRING,
                   temperatureCPU2Warning OCTET STRING,
                   temperatureCPU2WarningReset OCTET STRING,
                   temperatureCPU3HardShutdown OCTET STRING,
                   temperatureCPU3Warning OCTET STRING,
                   temperatureCPU3WarningReset OCTET STRING,
                   temperatureCPU4HardShutdown OCTET STRING,
                   temperatureCPU4Warning OCTET STRING,
                   temperatureCPU4WarningReset OCTET STRING,
                   temperatureDASD1HardShutdown OCTET STRING,
                   temperatureDASD1Warning OCTET STRING,
                   temperatureDASD1WarningReset OCTET STRING,
                   bladeTempThresholdSensorCapability INTEGER,
                   temperatureSensor1HardShutdown OCTET STRING,
                   temperatureSensor1Warning OCTET STRING,
                   temperatureSensor1WarningReset OCTET STRING,
                   temperatureSensor2HardShutdown OCTET STRING,
                   temperatureSensor2Warning OCTET STRING,
                   temperatureSensor2WarningReset OCTET STRING,
                   temperatureSensor3HardShutdown OCTET STRING,
                   temperatureSensor3Warning OCTET STRING,
                   temperatureSensor3WarningReset OCTET STRING,
                   temperatureSensor4HardShutdown OCTET STRING,
                   temperatureSensor4Warning OCTET STRING,
                   temperatureSensor4WarningReset OCTET STRING,
                   temperatureSensor5HardShutdown OCTET STRING,
                   temperatureSensor5Warning OCTET STRING,
                   temperatureSensor5WarningReset OCTET STRING,
                   temperatureSensor6HardShutdown OCTET STRING,
                   temperatureSensor6Warning OCTET STRING,
                   temperatureSensor6WarningReset OCTET STRING
       }

       temperatureThresholdIndex  OBJECT-TYPE
                   SYNTAX  INTEGER
                   ACCESS  read-only
                   STATUS  mandatory
                   DESCRIPTION
                   "Blade temperature threshold table index."
                   ::= { bladeTemperatureThresholdsEntry 1 }


       temperatureThresholdBladeId  OBJECT-TYPE
                   SYNTAX  INTEGER {
--                      managementModule(0),
                     blade1(1),
                     blade2(2),
                     blade3(3),
                     blade4(4),
                     blade5(5),
                     blade6(6),
                     blade7(7),
                     blade8(8),
                     blade9(9),
                     blade10(10),
                     blade11(11),
                     blade12(12),
                     blade13(13),
                     blade14(14)
                   }
                   ACCESS  read-only
                   STATUS  mandatory
                   DESCRIPTION
                   "The numeric blade ID."
                   ::= { bladeTemperatureThresholdsEntry 2 }

       temperatureThresholdBladeExists OBJECT-TYPE
                   SYNTAX  INTEGER {
                     false(0),
                     true(1)
                   }
                   ACCESS  read-only
                   STATUS  mandatory
                   DESCRIPTION
                   "Indicates whether the server blade specified exists or not."
                   ::= { bladeTemperatureThresholdsEntry 3 }

       temperatureThresholdBladePowerState OBJECT-TYPE
                   SYNTAX  INTEGER {
                     off(0),
                     on(1)
                   }
                   ACCESS  read-only
                   STATUS  mandatory
                   DESCRIPTION
                   "Indicates whether the server blade specified is powered on or not."
                   ::= { bladeTemperatureThresholdsEntry 4 }

       temperatureThresholdBladeName OBJECT-TYPE
                   SYNTAX  OCTET STRING
                   ACCESS  read-only
                   STATUS  mandatory
                   DESCRIPTION
                   "The name of the blade as a null terminated string."
                   ::= { bladeTemperatureThresholdsEntry 5 }

       temperatureCPU1HardShutdown OBJECT-TYPE
                   SYNTAX  OCTET STRING
                   ACCESS  read-only
                   STATUS  mandatory
                   DESCRIPTION
                   "The blade CPU hard shutdown temperature in degrees
                   centigrade(C).  If the component's temperature rises above
                   this value the system will be powered off immediately.
                   If enabled, a critical alert/event will be generated.
                   An octet string expressed as 'sddd.dd Centigrade' where:
                   s is the sign ('-' for negative or blank space for positive)
                   d is a decimal digit or blank space for a leading zero.
                   The string 'Not Readable!' indicates that the given monitor
                   is not supported on this system.
                   The string 'No Temperature' indicates that the given monitor
                   does not exist on this system or is powered off."
                   ::= { bladeTemperatureThresholdsEntry 6 }

       temperatureCPU1Warning OBJECT-TYPE
                   SYNTAX  OCTET STRING
                   ACCESS  read-only
                   STATUS  mandatory
                   DESCRIPTION
                   "The blade CPU warning temperature in degrees centigrade(C).
                   If the temperature rises above this value a warning alert/event
                   if enabled will be generated.
                   An octet string expressed as 'sddd.dd Centigrade' where:
                   s is the sign ('-' for negative or blank space for positive)
                   d is a decimal digit or blank space for a leading zero.
                   The string 'Not Readable!' indicates that the given monitor
                   is not supported on this system.
                   The string 'No Temperature' indicates that the given monitor
                   does not exist on this system or is powered off."
                   ::= { bladeTemperatureThresholdsEntry 7 }

       temperatureCPU1WarningReset OBJECT-TYPE
                   SYNTAX  OCTET STRING
                   ACCESS  read-only
                   STATUS  mandatory
                   DESCRIPTION
                   "The blade CPU warning reset temperature in degrees
                   centigrade(C).  If the temperature rises above this value and
                   if a warning alert/event had previously been created then the
                   alert/event will be reset.
                   An octet string expressed as 'sddd.dd Centigrade' where:
                   s is the sign ('-' for negative or blank space for positive)
                   d is a decimal digit or blank space for a leading zero.
                   The string 'Not Readable!' indicates that the given monitor
                   is not supported on this system.
                   The string 'No Temperature' indicates that the given monitor
                   does not exist on this system or is powered off."
                   ::= { bladeTemperatureThresholdsEntry 8 }

       temperatureCPU2HardShutdown OBJECT-TYPE
                   SYNTAX  OCTET STRING
                   ACCESS  read-only
                   STATUS  mandatory
                   DESCRIPTION
                   "The blade CPU hard shutdown temperature in degrees
                   centigrade(C).  If the component's temperature rises above
                   this value the system will be powered off immediately.
                   If enabled, a critical alert/event will be generated.
                   An octet string expressed as 'sddd.dd Centigrade' where:
                   s is the sign ('-' for negative or blank space for positive)
                   d is a decimal digit or blank space for a leading zero.
                   The string 'Not Readable!' indicates that the given monitor
                   is not supported on this system.
                   The string 'No Temperature' indicates that the given monitor
                   does not exist on this system or is powered off."
                   ::= { bladeTemperatureThresholdsEntry 9 }

       temperatureCPU2Warning OBJECT-TYPE
                   SYNTAX  OCTET STRING
                   ACCESS  read-only
                   STATUS  mandatory
                   DESCRIPTION
                   "The blade CPU warning temperature in degrees centigrade(C).
                   If the temperature rises above this value a warning alert/event
                   if enabled will be generated.
                   An octet string expressed as 'sddd.dd Centigrade' where:
                   s is the sign ('-' for negative or blank space for positive)
                   d is a decimal digit or blank space for a leading zero.
                   The string 'Not Readable!' indicates that the given monitor
                   is not supported on this system.
                   The string 'No Temperature' indicates that the given monitor
                   does not exist on this system or is powered off."
                   ::= { bladeTemperatureThresholdsEntry 10 }

       temperatureCPU2WarningReset OBJECT-TYPE
                   SYNTAX  OCTET STRING
                   ACCESS  read-only
                   STATUS  mandatory
                   DESCRIPTION
                   "The blade CPU warning reset temperature in degrees
                   centigrade(C).  If the temperature rises above this value and
                   if a warning alert/event had previously been created then the
                   alert/event will be reset.
                   An octet string expressed as 'sddd.dd Centigrade' where:
                   s is the sign ('-' for negative or blank space for positive)
                   d is a decimal digit or blank space for a leading zero.
                   The string 'Not Readable!' indicates that the given monitor
                   is not supported on this system.
                   The string 'No Temperature' indicates that the given monitor
                   does not exist on this system or is powered off."
                   ::= { bladeTemperatureThresholdsEntry 11 }

       temperatureCPU3HardShutdown OBJECT-TYPE
                   SYNTAX  OCTET STRING
                   ACCESS  read-only
                   STATUS  mandatory
                   DESCRIPTION
                   "The blade CPU hard shutdown temperature in degrees
                   centigrade(C).  If the component's temperature rises above
                   this value the system will be powered off immediately.
                   If enabled, a critical alert/event will be generated.
                   An octet string expressed as 'sddd.dd Centigrade' where:
                   s is the sign ('-' for negative or blank space for positive)
                   d is a decimal digit or blank space for a leading zero.
                   The string 'Not Readable!' indicates that the given monitor
                   is not supported on this system.
                   The string 'No Temperature' indicates that the given monitor
                   does not exist on this system or is powered off."
                   ::= { bladeTemperatureThresholdsEntry 12 }

       temperatureCPU3Warning OBJECT-TYPE
                   SYNTAX  OCTET STRING
                   ACCESS  read-only
                   STATUS  mandatory
                   DESCRIPTION
                   "The blade CPU warning temperature in degrees centigrade(C).
                   If the temperature rises above this value a warning alert/event
                   if enabled will be generated.
                   An octet string expressed as 'sddd.dd Centigrade' where:
                   s is the sign ('-' for negative or blank space for positive)
                   d is a decimal digit or blank space for a leading zero.
                   The string 'Not Readable!' indicates that the given monitor
                   is not supported on this system.
                   The string 'No Temperature' indicates that the given monitor
                   does not exist on this system or is powered off."
                   ::= { bladeTemperatureThresholdsEntry 13 }

       temperatureCPU3WarningReset OBJECT-TYPE
                   SYNTAX  OCTET STRING
                   ACCESS  read-only
                   STATUS  mandatory
                   DESCRIPTION
                   "The blade CPU warning reset temperature in degrees
                   centigrade(C).  If the temperature rises above this value and
                   if a warning alert/event had previously been created then the
                   alert/event will be reset.
                   An octet string expressed as 'sddd.dd Centigrade' where:
                   s is the sign ('-' for negative or blank space for positive)
                   d is a decimal digit or blank space for a leading zero.
                   The string 'Not Readable!' indicates that the given monitor
                   is not supported on this system.
                   The string 'No Temperature' indicates that the given monitor
                   does not exist on this system or is powered off."
                   ::= { bladeTemperatureThresholdsEntry 14 }

       temperatureCPU4HardShutdown OBJECT-TYPE
                   SYNTAX  OCTET STRING
                   ACCESS  read-only
                   STATUS  mandatory
                   DESCRIPTION
                   "The blade CPU hard shutdown temperature in degrees
                   centigrade(C).  If the component's temperature rises above
                   this value the system will be powered off immediately.
                   If enabled, a critical alert/event will be generated.
                   An octet string expressed as 'sddd.dd Centigrade' where:
                   s is the sign ('-' for negative or blank space for positive)
                   d is a decimal digit or blank space for a leading zero.
                   The string 'Not Readable!' indicates that the given monitor
                   is not supported on this system.
                   The string 'No Temperature' indicates that the given monitor
                   does not exist on this system or is powered off."
                   ::= { bladeTemperatureThresholdsEntry 15 }

       temperatureCPU4Warning OBJECT-TYPE
                   SYNTAX  OCTET STRING
                   ACCESS  read-only
                   STATUS  mandatory
                   DESCRIPTION
                   "The blade CPU warning temperature in degrees centigrade(C).
                   If the temperature rises above this value a warning alert/event
                   if enabled will be generated.
                   An octet string expressed as 'sddd.dd Centigrade' where:
                   s is the sign ('-' for negative or blank space for positive)
                   d is a decimal digit or blank space for a leading zero.
                   The string 'Not Readable!' indicates that the given monitor
                   is not supported on this system.
                   The string 'No Temperature' indicates that the given monitor
                   does not exist on this system or is powered off."
                   ::= { bladeTemperatureThresholdsEntry 16 }

       temperatureCPU4WarningReset OBJECT-TYPE
                   SYNTAX  OCTET STRING
                   ACCESS  read-only
                   STATUS  mandatory
                   DESCRIPTION
                   "The blade CPU warning reset temperature in degrees
                   centigrade(C).  If the temperature rises above this value and
                   if a warning alert/event had previously been created then the
                   alert/event will be reset.
                   An octet string expressed as 'sddd.dd Centigrade' where:
                   s is the sign ('-' for negative or blank space for positive)
                   d is a decimal digit or blank space for a leading zero.
                   The string 'Not Readable!' indicates that the given monitor
                   is not supported on this system.
                   The string 'No Temperature' indicates that the given monitor
                   does not exist on this system or is powered off."
                   ::= { bladeTemperatureThresholdsEntry 17 }

       temperatureDASD1HardShutdown OBJECT-TYPE
                   SYNTAX  OCTET STRING
                   ACCESS  read-only
                   STATUS  mandatory
                   DESCRIPTION
                   "The blade DASD hard shutdown temperature in degrees centigrade(C).
                   An octet string expressed as 'sddd.dd Centigrade' where:
                   s is the sign ('-' for negative or blank space for positive)
                   d is a decimal digit or blank space for leading zeroes.
                   The string 'Not Readable!' indicates that the given monitor
                   is not supported on this system.
                   The string 'No Temperature' indicates that the given monitor
                   does not exist on this system or is powered off."
                   ::= { bladeTemperatureThresholdsEntry 18 }

       temperatureDASD1Warning OBJECT-TYPE
                   SYNTAX  OCTET STRING
                   ACCESS  read-only
                   STATUS  mandatory
                   DESCRIPTION
                   "The blade DASD warning temperature in degrees centigrade(C).
                   An octet string expressed as 'sddd.dd Centigrade' where:
                   s is the sign ('-' for negative or blank space for positive)
                   d is a decimal digit or blank space for leading zeroes.
                   The string 'Not Readable!' indicates that the given monitor
                   is not supported on this system.
                   The string 'No Temperature' indicates that the given monitor
                   does not exist on this system or is powered off."
                   ::= { bladeTemperatureThresholdsEntry 19 }

       temperatureDASD1WarningReset OBJECT-TYPE
                   SYNTAX  OCTET STRING
                   ACCESS  read-only
                   STATUS  mandatory
                   DESCRIPTION
                   "The blade DASD warning reset temperature in degrees centigrade(C).
                   An octet string expressed as 'sddd.dd Centigrade' where:
                   s is the sign ('-' for negative or blank space for positive)
                   d is a decimal digit or blank space for leading zeroes.
                   The string 'Not Readable!' indicates that the given monitor
                   is not supported on this system.
                   The string 'No Temperature' indicates that the given monitor
                   does not exist on this system or is powered off."
                   ::= { bladeTemperatureThresholdsEntry 20 }
                   
       bladeTempThresholdSensorCapability OBJECT-TYPE
                   SYNTAX  INTEGER {
                     false(0),
                     true(1)
                   }
                   ACCESS  read-only
                   STATUS  mandatory
                   DESCRIPTION
                   "Indicates whether the server blade is IPMI capable or not."
                   ::= { bladeTemperatureThresholdsEntry 21 }

       temperatureSensor1HardShutdown OBJECT-TYPE
                   SYNTAX  OCTET STRING
                   ACCESS  read-only
                   STATUS  mandatory
                   DESCRIPTION
                   "The blade hard shutdown temperature for IPMI blades in degrees centigrade(C).
                   An octet string expressed as 'sddd.dd Centigrade' where:
                   s is the sign ('-' for negative or blank space for positive)
                   d is a decimal digit or blank space for leading zeroes.
                   The string 'Not Readable!' indicates that the given monitor
                   is not supported on this system.
                   The string 'No Temperature' indicates that the given monitor
                   does not exist on this system or is powered off."
                   ::= { bladeTemperatureThresholdsEntry 22 }

       temperatureSensor1Warning OBJECT-TYPE
                   SYNTAX  OCTET STRING
                   ACCESS  read-only
                   STATUS  mandatory
                   DESCRIPTION
                   "The blade hard shutdown temperature for IPMI blades in degrees centigrade(C).
                   An octet string expressed as 'sddd.dd Centigrade' where:
                   s is the sign ('-' for negative or blank space for positive)
                   d is a decimal digit or blank space for leading zeroes.
                   The string 'Not Readable!' indicates that the given monitor
                   is not supported on this system.
                   The string 'No Temperature' indicates that the given monitor
                   does not exist on this system or is powered off."
                   ::= { bladeTemperatureThresholdsEntry 23 }

       temperatureSensor1WarningReset OBJECT-TYPE
                   SYNTAX  OCTET STRING
                   ACCESS  read-only
                   STATUS  mandatory
                   DESCRIPTION
                   "The blade hard shutdown temperature for IPMI blades in degrees centigrade(C).
                   An octet string expressed as 'sddd.dd Centigrade' where:
                   s is the sign ('-' for negative or blank space for positive)
                   d is a decimal digit or blank space for leading zeroes.
                   The string 'Not Readable!' indicates that the given monitor
                   is not supported on this system.
                   The string 'No Temperature' indicates that the given monitor
                   does not exist on this system or is powered off."
                   ::= { bladeTemperatureThresholdsEntry 24 }

       temperatureSensor2HardShutdown OBJECT-TYPE
                   SYNTAX  OCTET STRING
                   ACCESS  read-only
                   STATUS  mandatory
                   DESCRIPTION
                   "The blade hard shutdown temperature for IPMI blades in degrees centigrade(C).
                   An octet string expressed as 'sddd.dd Centigrade' where:
                   s is the sign ('-' for negative or blank space for positive)
                   d is a decimal digit or blank space for leading zeroes.
                   The string 'Not Readable!' indicates that the given monitor
                   is not supported on this system.
                   The string 'No Temperature' indicates that the given monitor
                   does not exist on this system or is powered off."
                   ::= { bladeTemperatureThresholdsEntry 25 }

       temperatureSensor2Warning OBJECT-TYPE
                   SYNTAX  OCTET STRING
                   ACCESS  read-only
                   STATUS  mandatory
                   DESCRIPTION
                   "The blade hard shutdown temperature for IPMI blades in degrees centigrade(C).
                   An octet string expressed as 'sddd.dd Centigrade' where:
                   s is the sign ('-' for negative or blank space for positive)
                   d is a decimal digit or blank space for leading zeroes.
                   The string 'Not Readable!' indicates that the given monitor
                   is not supported on this system.
                   The string 'No Temperature' indicates that the given monitor
                   does not exist on this system or is powered off."
                   ::= { bladeTemperatureThresholdsEntry 26 }

       temperatureSensor2WarningReset OBJECT-TYPE
                   SYNTAX  OCTET STRING
                   ACCESS  read-only
                   STATUS  mandatory
                   DESCRIPTION
                   "The blade hard shutdown temperature for IPMI blades in degrees centigrade(C).
                   An octet string expressed as 'sddd.dd Centigrade' where:
                   s is the sign ('-' for negative or blank space for positive)
                   d is a decimal digit or blank space for leading zeroes.
                   The string 'Not Readable!' indicates that the given monitor
                   is not supported on this system.
                   The string 'No Temperature' indicates that the given monitor
                   does not exist on this system or is powered off."
                   ::= { bladeTemperatureThresholdsEntry 27 }

       temperatureSensor3HardShutdown OBJECT-TYPE
                   SYNTAX  OCTET STRING
                   ACCESS  read-only
                   STATUS  mandatory
                   DESCRIPTION
                   "The blade hard shutdown temperature for IPMI blades in degrees centigrade(C).
                   An octet string expressed as 'sddd.dd Centigrade' where:
                   s is the sign ('-' for negative or blank space for positive)
                   d is a decimal digit or blank space for leading zeroes.
                   The string 'Not Readable!' indicates that the given monitor
                   is not supported on this system.
                   The string 'No Temperature' indicates that the given monitor
                   does not exist on this system or is powered off."
                   ::= { bladeTemperatureThresholdsEntry 28 }

       temperatureSensor3Warning OBJECT-TYPE
                   SYNTAX  OCTET STRING
                   ACCESS  read-only
                   STATUS  mandatory
                   DESCRIPTION
                   "The blade hard shutdown temperature for IPMI blades in degrees centigrade(C).
                   An octet string expressed as 'sddd.dd Centigrade' where:
                   s is the sign ('-' for negative or blank space for positive)
                   d is a decimal digit or blank space for leading zeroes.
                   The string 'Not Readable!' indicates that the given monitor
                   is not supported on this system.
                   The string 'No Temperature' indicates that the given monitor
                   does not exist on this system or is powered off."
                   ::= { bladeTemperatureThresholdsEntry 29 }

       temperatureSensor3WarningReset OBJECT-TYPE
                   SYNTAX  OCTET STRING
                   ACCESS  read-only
                   STATUS  mandatory
                   DESCRIPTION
                   "The blade hard shutdown temperature for IPMI blades in degrees centigrade(C).
                   An octet string expressed as 'sddd.dd Centigrade' where:
                   s is the sign ('-' for negative or blank space for positive)
                   d is a decimal digit or blank space for leading zeroes.
                   The string 'Not Readable!' indicates that the given monitor
                   is not supported on this system.
                   The string 'No Temperature' indicates that the given monitor
                   does not exist on this system or is powered off."
                   ::= { bladeTemperatureThresholdsEntry 30 }

       temperatureSensor4HardShutdown OBJECT-TYPE
                   SYNTAX  OCTET STRING
                   ACCESS  read-only
                   STATUS  mandatory
                   DESCRIPTION
                   "The blade hard shutdown temperature for IPMI blades in degrees centigrade(C).
                   An octet string expressed as 'sddd.dd Centigrade' where:
                   s is the sign ('-' for negative or blank space for positive)
                   d is a decimal digit or blank space for leading zeroes.
                   The string 'Not Readable!' indicates that the given monitor
                   is not supported on this system.
                   The string 'No Temperature' indicates that the given monitor
                   does not exist on this system or is powered off."
                   ::= { bladeTemperatureThresholdsEntry 31 }

       temperatureSensor4Warning OBJECT-TYPE
                   SYNTAX  OCTET STRING
                   ACCESS  read-only
                   STATUS  mandatory
                   DESCRIPTION
                   "The blade hard shutdown temperature for IPMI blades in degrees centigrade(C).
                   An octet string expressed as 'sddd.dd Centigrade' where:
                   s is the sign ('-' for negative or blank space for positive)
                   d is a decimal digit or blank space for leading zeroes.
                   The string 'Not Readable!' indicates that the given monitor
                   is not supported on this system.
                   The string 'No Temperature' indicates that the given monitor
                   does not exist on this system or is powered off."
                   ::= { bladeTemperatureThresholdsEntry 32 }

       temperatureSensor4WarningReset OBJECT-TYPE
                   SYNTAX  OCTET STRING
                   ACCESS  read-only
                   STATUS  mandatory
                   DESCRIPTION
                   "The blade hard shutdown temperature for IPMI blades in degrees centigrade(C).
                   An octet string expressed as 'sddd.dd Centigrade' where:
                   s is the sign ('-' for negative or blank space for positive)
                   d is a decimal digit or blank space for leading zeroes.
                   The string 'Not Readable!' indicates that the given monitor
                   is not supported on this system.
                   The string 'No Temperature' indicates that the given monitor
                   does not exist on this system or is powered off."
                   ::= { bladeTemperatureThresholdsEntry 33 }

       temperatureSensor5HardShutdown OBJECT-TYPE
                   SYNTAX  OCTET STRING
                   ACCESS  read-only
                   STATUS  mandatory
                   DESCRIPTION
                   "The blade hard shutdown temperature for IPMI blades in degrees centigrade(C).
                   An octet string expressed as 'sddd.dd Centigrade' where:
                   s is the sign ('-' for negative or blank space for positive)
                   d is a decimal digit or blank space for leading zeroes.
                   The string 'Not Readable!' indicates that the given monitor
                   is not supported on this system.
                   The string 'No Temperature' indicates that the given monitor
                   does not exist on this system or is powered off."
                   ::= { bladeTemperatureThresholdsEntry 34 }

       temperatureSensor5Warning OBJECT-TYPE
                   SYNTAX  OCTET STRING
                   ACCESS  read-only
                   STATUS  mandatory
                   DESCRIPTION
                   "The blade hard shutdown temperature for IPMI blades in degrees centigrade(C).
                   An octet string expressed as 'sddd.dd Centigrade' where:
                   s is the sign ('-' for negative or blank space for positive)
                   d is a decimal digit or blank space for leading zeroes.
                   The string 'Not Readable!' indicates that the given monitor
                   is not supported on this system.
                   The string 'No Temperature' indicates that the given monitor
                   does not exist on this system or is powered off."
                   ::= { bladeTemperatureThresholdsEntry 35 }

       temperatureSensor5WarningReset OBJECT-TYPE
                   SYNTAX  OCTET STRING
                   ACCESS  read-only
                   STATUS  mandatory
                   DESCRIPTION
                   "The blade hard shutdown temperature for IPMI blades in degrees centigrade(C).
                   An octet string expressed as 'sddd.dd Centigrade' where:
                   s is the sign ('-' for negative or blank space for positive)
                   d is a decimal digit or blank space for leading zeroes.
                   The string 'Not Readable!' indicates that the given monitor
                   is not supported on this system.
                   The string 'No Temperature' indicates that the given monitor
                   does not exist on this system or is powered off."
                   ::= { bladeTemperatureThresholdsEntry 36 }

       temperatureSensor6HardShutdown OBJECT-TYPE
                   SYNTAX  OCTET STRING
                   ACCESS  read-only
                   STATUS  mandatory
                   DESCRIPTION
                   "The blade hard shutdown temperature for IPMI blades in degrees centigrade(C).
                   An octet string expressed as 'sddd.dd Centigrade' where:
                   s is the sign ('-' for negative or blank space for positive)
                   d is a decimal digit or blank space for leading zeroes.
                   The string 'Not Readable!' indicates that the given monitor
                   is not supported on this system.
                   The string 'No Temperature' indicates that the given monitor
                   does not exist on this system or is powered off."
                   ::= { bladeTemperatureThresholdsEntry 37 }

       temperatureSensor6Warning OBJECT-TYPE
                   SYNTAX  OCTET STRING
                   ACCESS  read-only
                   STATUS  mandatory
                   DESCRIPTION
                   "The blade hard shutdown temperature for IPMI blades in degrees centigrade(C).
                   An octet string expressed as 'sddd.dd Centigrade' where:
                   s is the sign ('-' for negative or blank space for positive)
                   d is a decimal digit or blank space for leading zeroes.
                   The string 'Not Readable!' indicates that the given monitor
                   is not supported on this system.
                   The string 'No Temperature' indicates that the given monitor
                   does not exist on this system or is powered off."
                   ::= { bladeTemperatureThresholdsEntry 38 }

       temperatureSensor6WarningReset OBJECT-TYPE
                   SYNTAX  OCTET STRING
                   ACCESS  read-only
                   STATUS  mandatory
                   DESCRIPTION
                   "The blade hard shutdown temperature for IPMI blades in degrees centigrade(C).
                   An octet string expressed as 'sddd.dd Centigrade' where:
                   s is the sign ('-' for negative or blank space for positive)
                   d is a decimal digit or blank space for leading zeroes.
                   The string 'Not Readable!' indicates that the given monitor
                   is not supported on this system.
                   The string 'No Temperature' indicates that the given monitor
                   does not exist on this system or is powered off."
                   ::= { bladeTemperatureThresholdsEntry 39 }



      bladeVoltagesTable OBJECT-TYPE
                     SYNTAX  SEQUENCE OF BladeVoltagesEntry
                     ACCESS  not-accessible
                     STATUS  mandatory
                     DESCRIPTION
                     "Table of blade voltages information."
                     ::= { bladeMonitors 5 }

       bladeVoltagesEntry OBJECT-TYPE
                     SYNTAX BladeVoltagesEntry
                     ACCESS  not-accessible
                     STATUS  mandatory
                     DESCRIPTION
                     "Blade voltages table entry"
                     INDEX { voltageIndex }
                     ::= { bladeVoltagesTable 1 }

       BladeVoltagesEntry ::= SEQUENCE {
                   voltageIndex INTEGER,
                   voltageBladeId INTEGER,
                   voltageBladeExists INTEGER,
                   voltageBladePowerState INTEGER,
                   voltageBladeName OCTET STRING,
--                 voltageBladeName OCTET STRING,
                   bladePlus5Volt OCTET STRING,
                   bladePlus3pt3Volt OCTET STRING,
                   bladePlus12Volt OCTET STRING,
--                 bladeMinus12Volt OCTET STRING,
                   bladePlus2pt5Volt OCTET STRING,
                   bladePlus1pt5Volt OCTET STRING,
                   bladePlus1pt25Volt OCTET STRING,
                   bladeVRM1Volt OCTET STRING,
                   bladeSensorVoltCapability INTEGER,
                   bladeSensor1Volt OCTET STRING,
                   bladeSensor2Volt OCTET STRING,
                   bladeSensor3Volt OCTET STRING,
                   bladeSensor4Volt OCTET STRING,
                   bladeSensor5Volt OCTET STRING,
                   bladeSensor6Volt OCTET STRING,
                   bladeSensor7Volt OCTET STRING,
                   bladeSensor8Volt OCTET STRING,
                   bladeSensor9Volt OCTET STRING,
                   bladeSensor10Volt OCTET STRING,
                   bladeSensor11Volt OCTET STRING,
                   bladeSensor12Volt OCTET STRING,
                   bladeSensor13Volt OCTET STRING,
                   bladeSensor14Volt OCTET STRING,
                   bladeSensor15Volt OCTET STRING,
                   bladeSensor16Volt OCTET STRING,
                   bladeSensor17Volt OCTET STRING,
                   bladeSensor18Volt OCTET STRING,
                   bladeSensor19Volt OCTET STRING,
                   bladeSensor20Volt OCTET STRING,
                   bladeSensor21Volt OCTET STRING,
                   bladeSensor22Volt OCTET STRING,
                   bladeSensor23Volt OCTET STRING,
                   bladeSensor24Volt OCTET STRING,
                   bladeSensor25Volt OCTET STRING, 
                   bladeSensor26Volt OCTET STRING, 
                   bladeSensor27Volt OCTET STRING, 
                   bladeSensor28Volt OCTET STRING, 
                   bladeSensor29Volt OCTET STRING, 
                   bladeSensor30Volt OCTET STRING 
       }

       voltageIndex  OBJECT-TYPE
                   SYNTAX  INTEGER
                   ACCESS  read-only
                   STATUS  mandatory
                   DESCRIPTION
                   "Blade voltages table index."
                   ::= { bladeVoltagesEntry 1 }


       voltageBladeId  OBJECT-TYPE
                   SYNTAX  INTEGER {
--                      managementModule(0),
                     blade1(1),
                     blade2(2),
                     blade3(3),
                     blade4(4),
                     blade5(5),
                     blade6(6),
                     blade7(7),
                     blade8(8),
                     blade9(9),
                     blade10(10),
                     blade11(11),
                     blade12(12),
                     blade13(13),
                     blade14(14)
                   }
                   ACCESS  read-only
                   STATUS  mandatory
                   DESCRIPTION
                   "The numeric blade ID."
                   ::= { bladeVoltagesEntry 2 }

       voltageBladeExists OBJECT-TYPE
                   SYNTAX  INTEGER {
                     false(0),
                     true(1)
                   }
                   ACCESS  read-only
                   STATUS  mandatory
                   DESCRIPTION
                   "Indicates whether the server blade specified exists or not."
                   ::= { bladeVoltagesEntry 3 }

       voltageBladePowerState OBJECT-TYPE
                   SYNTAX  INTEGER {
                     off(0),
                     on(1)
                   }
                   ACCESS  read-only
                   STATUS  mandatory
                   DESCRIPTION
                   "Indicates whether the server blade specified is powered on or not."
                   ::= { bladeVoltagesEntry 4 }

       voltageBladeName OBJECT-TYPE
                   SYNTAX  OCTET STRING
                   ACCESS  read-only
                   STATUS  mandatory
                   DESCRIPTION
                   "The name of the blade as a null terminated string."
                   ::= { bladeVoltagesEntry 5 }

       bladePlus5Volt OBJECT-TYPE
                   SYNTAX  OCTET STRING
                   ACCESS  read-only
                   STATUS  mandatory
                   DESCRIPTION
                   "+5 Volt power supply voltage reading for the blade
                   expressed in Volts(V).  An octet string expressed as
                   'sdd.dd Volts' where:
                   s is the sign ('-' for negative or '+' for positive)
                   d is a decimal digit or blank space for a leading zero.
                   The string 'Not Readable!' indicates that the given monitor
                   is not supported on this system.
                   The string 'No Voltage' indicates that the given monitor
                   does not exist on this system or is powered off."
                   ::= { bladeVoltagesEntry 6 }

       bladePlus3pt3Volt OBJECT-TYPE
                   SYNTAX  OCTET STRING
                   ACCESS  read-only
                   STATUS  mandatory
                   DESCRIPTION
                   "+3.3 Volt power supply voltage reading for the blade
                   expressed in Volts(V).  An octet string expressed as
                   'sdd.dd Volts' where:
                   s is the sign ('-' for negative or '+' for positive)
                   d is a decimal digit or blank space for a leading zero.
                   The string 'Not Readable!' indicates that the given monitor
                   is not supported on this system.
                   The string 'No Voltage' indicates that the given monitor
                   does not exist on this system or is powered off."
                   ::= { bladeVoltagesEntry 7 }

       bladePlus12Volt OBJECT-TYPE
                   SYNTAX  OCTET STRING
                   ACCESS  read-only
                   STATUS  mandatory
                   DESCRIPTION
                   "+12 Volt power supply voltage reading for the blade
                   expressed in Volts(V).  An octet string expressed as
                   'sdd.dd Volts' where:
                   s is the sign ('-' for negative or '+' for positive)
                   d is a decimal digit or blank space for a leading zero.
                   The string 'Not Readable!' indicates that the given monitor
                   is not supported on this system.
                   The string 'No Voltage' indicates that the given monitor
                   does not exist on this system or is powered off."
                   ::= { bladeVoltagesEntry 8 }

--     bladeMinus12Volt OBJECT-TYPE
--                 SYNTAX  OCTET STRING
--                 ACCESS  read-only
--                 STATUS  mandatory
--                 DESCRIPTION
--                 "-12 Volt power supply voltage reading for the blade
--                 expressed in Volts(V).  An octet string expressed as
--                 'sdd.dd Volts' where:
--                 s is the sign ('-' for negative or '+' for positive)
--                 d is a decimal digit or blank space for a leading zero.
--                 The string 'Not Readable!' indicates that the given monitor
--                 is not supported on this system."
--                 ::= { bladeVoltagesEntry 9 }

       bladePlus2pt5Volt OBJECT-TYPE
                   SYNTAX  OCTET STRING
                   ACCESS  read-only
                   STATUS  mandatory
                   DESCRIPTION
                   "+2.5 Volt power supply voltage reading for the blade
                   expressed in Volts(V).  An octet string expressed as
                   'sdd.dd Volts' where:
                   s is the sign ('-' for negative or '+' for positive)
                   d is a decimal digit or blank space for a leading zero.
                   The string 'Not Readable!' indicates that the given monitor
                   is not supported on this system.
                   The string 'No Voltage' indicates that the given monitor
                   does not exist on this system or is powered off."
                   ::= { bladeVoltagesEntry 10 }

       bladePlus1pt5Volt OBJECT-TYPE
                   SYNTAX  OCTET STRING
                   ACCESS  read-only
                   STATUS  mandatory
                   DESCRIPTION
                   "+1.5 Volt power supply voltage reading for the blade
                   expressed in Volts(V).  An octet string expressed as
                   'sdd.dd Volts' where:
                   s is the sign ('-' for negative or '+' for positive)
                   d is a decimal digit or blank space for a leading zero.
                   The string 'Not Readable!' indicates that the given monitor
                   is not supported on this system.
                   The string 'No Voltage' indicates that the given monitor
                   does not exist on this system or is powered off."
                   ::= { bladeVoltagesEntry 11 }

       bladePlus1pt25Volt OBJECT-TYPE
                   SYNTAX  OCTET STRING
                   ACCESS  read-only
                   STATUS  mandatory
                   DESCRIPTION
                   "+1.25 Volt power supply voltage reading for the blade
                   expressed in Volts(V).  An octet string expressed as
                   'sdd.dd Volts' where:
                   s is the sign ('-' for negative or '+' for positive)
                   d is a decimal digit or blank space for a leading zero.
                   The string 'Not Readable!' indicates that the given monitor
                   is not supported on this system.
                   The string 'No Voltage' indicates that the given monitor
                   does not exist on this system or is powered off."
                   ::= { bladeVoltagesEntry 12 }

       bladeVRM1Volt OBJECT-TYPE
                   SYNTAX  OCTET STRING
                   ACCESS  read-only
                   STATUS  mandatory
                   DESCRIPTION
                   "VRM 1 voltage reading for the blade expressed in Volts(V).
                   An octet string expressed as 'sdd.dd Volts' where:
                   s is the sign ('-' for negative or '+' for positive)
                   d is a decimal digit or blank space for a leading zero.
                   The string 'Not Readable!' indicates that the given monitor
                   is not supported on this system.
                   The string 'No Voltage' indicates that the given monitor
                   does not exist on this system or is powered off."
                   ::= { bladeVoltagesEntry 13 }

       bladeSensorVoltCapability OBJECT-TYPE
                   SYNTAX  INTEGER {
                     false(0),
                     true(1)
                   }
                   ACCESS  read-only
                   STATUS  mandatory
                   DESCRIPTION
                   "Indicates whether the server blade is IPMI capable or not."
                   ::= { bladeVoltagesEntry 14 }
                   
       bladeSensor1Volt OBJECT-TYPE
                   SYNTAX  OCTET STRING
                   ACCESS  read-only
                   STATUS  mandatory
                   DESCRIPTION
                   "Voltage reading for an IPMI blade expressed in Volts(V).
                   An octet string expressed as 'sdd.dd Volts' where:
                   s is the sign ('-' for negative or '+' for positive)
                   d is a decimal digit or blank space for a leading zero.
                   The string 'Not Readable!' indicates that the given monitor
                   is not supported on this system.
                   The string 'No Voltage' indicates that the given monitor
                   does not exist on this system or is powered off."
                   ::= { bladeVoltagesEntry 15 }

       bladeSensor2Volt OBJECT-TYPE
                   SYNTAX  OCTET STRING
                   ACCESS  read-only
                   STATUS  mandatory
                   DESCRIPTION
                   "Voltage reading for an IPMI blade expressed in Volts(V).
                   An octet string expressed as 'sdd.dd Volts' where:
                   s is the sign ('-' for negative or '+' for positive)
                   d is a decimal digit or blank space for a leading zero.
                   The string 'Not Readable!' indicates that the given monitor
                   is not supported on this system.
                   The string 'No Voltage' indicates that the given monitor
                   does not exist on this system or is powered off."
                   ::= { bladeVoltagesEntry 16 }

       bladeSensor3Volt OBJECT-TYPE
                   SYNTAX  OCTET STRING
                   ACCESS  read-only
                   STATUS  mandatory
                   DESCRIPTION
                   "Voltage reading for an IPMI blade expressed in Volts(V).
                   An octet string expressed as 'sdd.dd Volts' where:
                   s is the sign ('-' for negative or '+' for positive)
                   d is a decimal digit or blank space for a leading zero.
                   The string 'Not Readable!' indicates that the given monitor
                   is not supported on this system.
                   The string 'No Voltage' indicates that the given monitor
                   does not exist on this system or is powered off."
                   ::= { bladeVoltagesEntry 17 }

       bladeSensor4Volt OBJECT-TYPE
                   SYNTAX  OCTET STRING
                   ACCESS  read-only
                   STATUS  mandatory
                   DESCRIPTION
                   "Voltage reading for an IPMI blade expressed in Volts(V).
                   An octet string expressed as 'sdd.dd Volts' where:
                   s is the sign ('-' for negative or '+' for positive)
                   d is a decimal digit or blank space for a leading zero.
                   The string 'Not Readable!' indicates that the given monitor
                   is not supported on this system.
                   The string 'No Voltage' indicates that the given monitor
                   does not exist on this system or is powered off."
                   ::= { bladeVoltagesEntry 18 }

       bladeSensor5Volt OBJECT-TYPE
                   SYNTAX  OCTET STRING
                   ACCESS  read-only
                   STATUS  mandatory
                   DESCRIPTION
                   "Voltage reading for an IPMI blade expressed in Volts(V).
                   An octet string expressed as 'sdd.dd Volts' where:
                   s is the sign ('-' for negative or '+' for positive)
                   d is a decimal digit or blank space for a leading zero.
                   The string 'Not Readable!' indicates that the given monitor
                   is not supported on this system.
                   The string 'No Voltage' indicates that the given monitor
                   does not exist on this system or is powered off."
                   ::= { bladeVoltagesEntry 19 }

       bladeSensor6Volt OBJECT-TYPE
                   SYNTAX  OCTET STRING
                   ACCESS  read-only
                   STATUS  mandatory
                   DESCRIPTION
                   "Voltage reading for an IPMI blade expressed in Volts(V).
                   An octet string expressed as 'sdd.dd Volts' where:
                   s is the sign ('-' for negative or '+' for positive)
                   d is a decimal digit or blank space for a leading zero.
                   The string 'Not Readable!' indicates that the given monitor
                   is not supported on this system.
                   The string 'No Voltage' indicates that the given monitor
                   does not exist on this system or is powered off."
                   ::= { bladeVoltagesEntry 20 }

       bladeSensor7Volt OBJECT-TYPE
                   SYNTAX  OCTET STRING
                   ACCESS  read-only
                   STATUS  mandatory
                   DESCRIPTION
                   "Voltage reading for an IPMI blade expressed in Volts(V).
                   An octet string expressed as 'sdd.dd Volts' where:
                   s is the sign ('-' for negative or '+' for positive)
                   d is a decimal digit or blank space for a leading zero.
                   The string 'Not Readable!' indicates that the given monitor
                   is not supported on this system.
                   The string 'No Voltage' indicates that the given monitor
                   does not exist on this system or is powered off."
                   ::= { bladeVoltagesEntry 21 }

       bladeSensor8Volt OBJECT-TYPE
                   SYNTAX  OCTET STRING
                   ACCESS  read-only
                   STATUS  mandatory
                   DESCRIPTION
                   "Voltage reading for an IPMI blade expressed in Volts(V).
                   An octet string expressed as 'sdd.dd Volts' where:
                   s is the sign ('-' for negative or '+' for positive)
                   d is a decimal digit or blank space for a leading zero.
                   The string 'Not Readable!' indicates that the given monitor
                   is not supported on this system.
                   The string 'No Voltage' indicates that the given monitor
                   does not exist on this system or is powered off."
                   ::= { bladeVoltagesEntry 22 }

       bladeSensor9Volt OBJECT-TYPE
                   SYNTAX  OCTET STRING
                   ACCESS  read-only
                   STATUS  mandatory
                   DESCRIPTION
                   "Voltage reading for an IPMI blade expressed in Volts(V).
                   An octet string expressed as 'sdd.dd Volts' where:
                   s is the sign ('-' for negative or '+' for positive)
                   d is a decimal digit or blank space for a leading zero.
                   The string 'Not Readable!' indicates that the given monitor
                   is not supported on this system.
                   The string 'No Voltage' indicates that the given monitor
                   does not exist on this system or is powered off."
                   ::= { bladeVoltagesEntry 23 }

       bladeSensor10Volt OBJECT-TYPE
                   SYNTAX  OCTET STRING
                   ACCESS  read-only
                   STATUS  mandatory
                   DESCRIPTION
                   "Voltage reading for an IPMI blade expressed in Volts(V).
                   An octet string expressed as 'sdd.dd Volts' where:
                   s is the sign ('-' for negative or '+' for positive)
                   d is a decimal digit or blank space for a leading zero.
                   The string 'Not Readable!' indicates that the given monitor
                   is not supported on this system.
                   The string 'No Voltage' indicates that the given monitor
                   does not exist on this system or is powered off."
                   ::= { bladeVoltagesEntry 24 }

       bladeSensor11Volt OBJECT-TYPE
                   SYNTAX  OCTET STRING
                   ACCESS  read-only
                   STATUS  mandatory
                   DESCRIPTION
                   "Voltage reading for an IPMI blade expressed in Volts(V).
                   An octet string expressed as 'sdd.dd Volts' where:
                   s is the sign ('-' for negative or '+' for positive)
                   d is a decimal digit or blank space for a leading zero.
                   The string 'Not Readable!' indicates that the given monitor
                   is not supported on this system.
                   The string 'No Voltage' indicates that the given monitor
                   does not exist on this system or is powered off."
                   ::= { bladeVoltagesEntry 25 }

       bladeSensor12Volt OBJECT-TYPE
                   SYNTAX  OCTET STRING
                   ACCESS  read-only
                   STATUS  mandatory
                   DESCRIPTION
                   "Voltage reading for an IPMI blade expressed in Volts(V).
                   An octet string expressed as 'sdd.dd Volts' where:
                   s is the sign ('-' for negative or '+' for positive)
                   d is a decimal digit or blank space for a leading zero.
                   The string 'Not Readable!' indicates that the given monitor
                   is not supported on this system.
                   The string 'No Voltage' indicates that the given monitor
                   does not exist on this system or is powered off."
                   ::= { bladeVoltagesEntry 26 }

       bladeSensor13Volt OBJECT-TYPE
                   SYNTAX  OCTET STRING
                   ACCESS  read-only
                   STATUS  mandatory
                   DESCRIPTION
                   "Voltage reading for an IPMI blade expressed in Volts(V).
                   An octet string expressed as 'sdd.dd Volts' where:
                   s is the sign ('-' for negative or '+' for positive)
                   d is a decimal digit or blank space for a leading zero.
                   The string 'Not Readable!' indicates that the given monitor
                   is not supported on this system.
                   The string 'No Voltage' indicates that the given monitor
                   does not exist on this system or is powered off."
                   ::= { bladeVoltagesEntry 27 }

       bladeSensor14Volt OBJECT-TYPE
                   SYNTAX  OCTET STRING
                   ACCESS  read-only
                   STATUS  mandatory
                   DESCRIPTION
                   "Voltage reading for an IPMI blade expressed in Volts(V).
                   An octet string expressed as 'sdd.dd Volts' where:
                   s is the sign ('-' for negative or '+' for positive)
                   d is a decimal digit or blank space for a leading zero.
                   The string 'Not Readable!' indicates that the given monitor
                   is not supported on this system.
                   The string 'No Voltage' indicates that the given monitor
                   does not exist on this system or is powered off."
                   ::= { bladeVoltagesEntry 28 }

       bladeSensor15Volt OBJECT-TYPE
                   SYNTAX  OCTET STRING
                   ACCESS  read-only
                   STATUS  mandatory
                   DESCRIPTION
                   "Voltage reading for an IPMI blade expressed in Volts(V).
                   An octet string expressed as 'sdd.dd Volts' where:
                   s is the sign ('-' for negative or '+' for positive)
                   d is a decimal digit or blank space for a leading zero.
                   The string 'Not Readable!' indicates that the given monitor
                   is not supported on this system.
                   The string 'No Voltage' indicates that the given monitor
                   does not exist on this system or is powered off."
                   ::= { bladeVoltagesEntry 29 }

       bladeSensor16Volt OBJECT-TYPE
                   SYNTAX  OCTET STRING
                   ACCESS  read-only
                   STATUS  mandatory
                   DESCRIPTION
                   "Voltage reading for an IPMI blade expressed in Volts(V).
                   An octet string expressed as 'sdd.dd Volts' where:
                   s is the sign ('-' for negative or '+' for positive)
                   d is a decimal digit or blank space for a leading zero.
                   The string 'Not Readable!' indicates that the given monitor
                   is not supported on this system.
                   The string 'No Voltage' indicates that the given monitor
                   does not exist on this system or is powered off."
                   ::= { bladeVoltagesEntry 30 }

       bladeSensor17Volt OBJECT-TYPE
                   SYNTAX  OCTET STRING
                   ACCESS  read-only
                   STATUS  mandatory
                   DESCRIPTION
                   "Voltage reading for an IPMI blade expressed in Volts(V).
                   An octet string expressed as 'sdd.dd Volts' where:
                   s is the sign ('-' for negative or '+' for positive)
                   d is a decimal digit or blank space for a leading zero.
                   The string 'Not Readable!' indicates that the given monitor
                   is not supported on this system.
                   The string 'No Voltage' indicates that the given monitor
                   does not exist on this system or is powered off."
                   ::= { bladeVoltagesEntry 31 }

       bladeSensor18Volt OBJECT-TYPE
                   SYNTAX  OCTET STRING
                   ACCESS  read-only
                   STATUS  mandatory
                   DESCRIPTION
                   "Voltage reading for an IPMI blade expressed in Volts(V).
                   An octet string expressed as 'sdd.dd Volts' where:
                   s is the sign ('-' for negative or '+' for positive)
                   d is a decimal digit or blank space for a leading zero.
                   The string 'Not Readable!' indicates that the given monitor
                   is not supported on this system.
                   The string 'No Voltage' indicates that the given monitor
                   does not exist on this system or is powered off."
                   ::= { bladeVoltagesEntry 32 }

       bladeSensor19Volt OBJECT-TYPE
                   SYNTAX  OCTET STRING
                   ACCESS  read-only
                   STATUS  mandatory
                   DESCRIPTION
                   "Voltage reading for an IPMI blade expressed in Volts(V).
                   An octet string expressed as 'sdd.dd Volts' where:
                   s is the sign ('-' for negative or '+' for positive)
                   d is a decimal digit or blank space for a leading zero.
                   The string 'Not Readable!' indicates that the given monitor
                   is not supported on this system.
                   The string 'No Voltage' indicates that the given monitor
                   does not exist on this system or is powered off."
                   ::= { bladeVoltagesEntry 33 }

       bladeSensor20Volt OBJECT-TYPE
                   SYNTAX  OCTET STRING
                   ACCESS  read-only
                   STATUS  mandatory
                   DESCRIPTION
                   "Voltage reading for an IPMI blade expressed in Volts(V).
                   An octet string expressed as 'sdd.dd Volts' where:
                   s is the sign ('-' for negative or '+' for positive)
                   d is a decimal digit or blank space for a leading zero.
                   The string 'Not Readable!' indicates that the given monitor
                   is not supported on this system.
                   The string 'No Voltage' indicates that the given monitor
                   does not exist on this system or is powered off."
                   ::= { bladeVoltagesEntry 34 }

       bladeSensor21Volt OBJECT-TYPE
                   SYNTAX  OCTET STRING
                   ACCESS  read-only
                   STATUS  mandatory
                   DESCRIPTION
                   "Voltage reading for an IPMI blade expressed in Volts(V).
                   An octet string expressed as 'sdd.dd Volts' where:
                   s is the sign ('-' for negative or '+' for positive)
                   d is a decimal digit or blank space for a leading zero.
                   The string 'Not Readable!' indicates that the given monitor
                   is not supported on this system.
                   The string 'No Voltage' indicates that the given monitor
                   does not exist on this system or is powered off."
                   ::= { bladeVoltagesEntry 35 }

       bladeSensor22Volt OBJECT-TYPE
                   SYNTAX  OCTET STRING
                   ACCESS  read-only
                   STATUS  mandatory
                   DESCRIPTION
                   "Voltage reading for an IPMI blade expressed in Volts(V).
                   An octet string expressed as 'sdd.dd Volts' where:
                   s is the sign ('-' for negative or '+' for positive)
                   d is a decimal digit or blank space for a leading zero.
                   The string 'Not Readable!' indicates that the given monitor
                   is not supported on this system.
                   The string 'No Voltage' indicates that the given monitor
                   does not exist on this system or is powered off."
                   ::= { bladeVoltagesEntry 36 }

       bladeSensor23Volt OBJECT-TYPE
                   SYNTAX  OCTET STRING
                   ACCESS  read-only
                   STATUS  mandatory
                   DESCRIPTION
                   "Voltage reading for an IPMI blade expressed in Volts(V).
                   An octet string expressed as 'sdd.dd Volts' where:
                   s is the sign ('-' for negative or '+' for positive)
                   d is a decimal digit or blank space for a leading zero.
                   The string 'Not Readable!' indicates that the given monitor
                   is not supported on this system.
                   The string 'No Voltage' indicates that the given monitor
                   does not exist on this system or is powered off."
                   ::= { bladeVoltagesEntry 37 }

       bladeSensor24Volt OBJECT-TYPE
                   SYNTAX  OCTET STRING
                   ACCESS  read-only
                   STATUS  mandatory
                   DESCRIPTION
                   "Voltage reading for an IPMI blade expressed in Volts(V).
                   An octet string expressed as 'sdd.dd Volts' where:
                   s is the sign ('-' for negative or '+' for positive)
                   d is a decimal digit or blank space for a leading zero.
                   The string 'Not Readable!' indicates that the given monitor
                   is not supported on this system.
                   The string 'No Voltage' indicates that the given monitor
                   does not exist on this system or is powered off."
                   ::= { bladeVoltagesEntry 38 }

       bladeSensor25Volt OBJECT-TYPE
                   SYNTAX  OCTET STRING
                   ACCESS  read-only
                   STATUS  mandatory
                   DESCRIPTION
                   "Voltage reading for an IPMI blade expressed in Volts(V).
                   An octet string expressed as 'sdd.dd Volts' where:
                   s is the sign ('-' for negative or '+' for positive)
                   d is a decimal digit or blank space for a leading zero.
                   The string 'Not Readable!' indicates that the given monitor
                   is not supported on this system.
                   The string 'No Voltage' indicates that the given monitor
                   does not exist on this system or is powered off."
                   ::= { bladeVoltagesEntry 39 }

       bladeSensor26Volt OBJECT-TYPE
                   SYNTAX  OCTET STRING
                   ACCESS  read-only
                   STATUS  mandatory
                   DESCRIPTION
                   "Voltage reading for an IPMI blade expressed in Volts(V).
                   An octet string expressed as 'sdd.dd Volts' where:
                   s is the sign ('-' for negative or '+' for positive)
                   d is a decimal digit or blank space for a leading zero.
                   The string 'Not Readable!' indicates that the given monitor
                   is not supported on this system.
                   The string 'No Voltage' indicates that the given monitor
                   does not exist on this system or is powered off."
                   ::= { bladeVoltagesEntry 40 }

       bladeSensor27Volt OBJECT-TYPE
                   SYNTAX  OCTET STRING
                   ACCESS  read-only
                   STATUS  mandatory
                   DESCRIPTION
                   "Voltage reading for an IPMI blade expressed in Volts(V).
                   An octet string expressed as 'sdd.dd Volts' where:
                   s is the sign ('-' for negative or '+' for positive)
                   d is a decimal digit or blank space for a leading zero.
                   The string 'Not Readable!' indicates that the given monitor
                   is not supported on this system.
                   The string 'No Voltage' indicates that the given monitor
                   does not exist on this system or is powered off."
                   ::= { bladeVoltagesEntry 41 }
      
      
       bladeSensor28Volt OBJECT-TYPE
                   SYNTAX  OCTET STRING
                   ACCESS  read-only
                   STATUS  mandatory
                   DESCRIPTION
                   "Voltage reading for an IPMI blade expressed in Volts(V).
                   An octet string expressed as 'sdd.dd Volts' where:
                   s is the sign ('-' for negative or '+' for positive)
                   d is a decimal digit or blank space for a leading zero.
                   The string 'Not Readable!' indicates that the given monitor
                   is not supported on this system.
                   The string 'No Voltage' indicates that the given monitor
                   does not exist on this system or is powered off."
                   ::= { bladeVoltagesEntry 42 }
      
       bladeSensor29Volt OBJECT-TYPE
                   SYNTAX  OCTET STRING
                   ACCESS  read-only
                   STATUS  mandatory
                   DESCRIPTION
                   "Voltage reading for an IPMI blade expressed in Volts(V).
                   An octet string expressed as 'sdd.dd Volts' where:
                   s is the sign ('-' for negative or '+' for positive)
                   d is a decimal digit or blank space for a leading zero.
                   The string 'Not Readable!' indicates that the given monitor
                   is not supported on this system.
                   The string 'No Voltage' indicates that the given monitor
                   does not exist on this system or is powered off."
                   ::= { bladeVoltagesEntry 43 }
      
       bladeSensor30Volt OBJECT-TYPE
                   SYNTAX  OCTET STRING
                   ACCESS  read-only
                   STATUS  mandatory
                   DESCRIPTION
                   "Voltage reading for an IPMI blade expressed in Volts(V).
                   An octet string expressed as 'sdd.dd Volts' where:
                   s is the sign ('-' for negative or '+' for positive)
                   d is a decimal digit or blank space for a leading zero.
                   The string 'Not Readable!' indicates that the given monitor
                   is not supported on this system.
                   The string 'No Voltage' indicates that the given monitor
                   does not exist on this system or is powered off."
                   ::= { bladeVoltagesEntry 44 }
      
      
      bladeVoltageThresholdsTable OBJECT-TYPE
                     SYNTAX  SEQUENCE OF BladeVoltageThresholdsEntry
                     ACCESS  not-accessible
                     STATUS  mandatory
                     DESCRIPTION
                     "Table of blade VoltageThresholds information."
                     ::= { bladeMonitors 6 }


       bladeVoltageThresholdsEntry OBJECT-TYPE
                     SYNTAX BladeVoltageThresholdsEntry
                     ACCESS  not-accessible
                     STATUS  mandatory
                     DESCRIPTION
                     "Blade voltage thresholds table entry"
                     INDEX { voltageThresholdIndex }
                     ::= { bladeVoltageThresholdsTable 1 }


       BladeVoltageThresholdsEntry ::= SEQUENCE {
                   voltageThresholdIndex INTEGER,
                   voltageThresholdBladeId INTEGER,
                   voltageThresholdBladeExists INTEGER,
                   voltageThresholdBladePowerState INTEGER,
                   voltageThresholdBladeName OCTET STRING,
                   bladePlus5VoltHighWarning OCTET STRING,
                   bladePlus5VoltLowWarning OCTET STRING,
                   bladePlus3pt3VoltHighWarning OCTET STRING,
                   bladePlus3pt3VoltLowWarning OCTET STRING,
                   bladePlus12VoltHighWarning OCTET STRING,
                   bladePlus12VoltLowWarning OCTET STRING,
--                 bladeMinus12VoltHighWarning OCTET STRING,
--                 bladeMinus12VoltLowWarning OCTET STRING,
                   bladePlus2pt5VoltHighWarning OCTET STRING,
                   bladePlus2pt5VoltLowWarning OCTET STRING,
                   bladePlus1pt5VoltHighWarning OCTET STRING,
                   bladePlus1pt5VoltLowWarning OCTET STRING,
                   bladePlus1pt25VoltHighWarning OCTET STRING,
                   bladePlus1pt25VoltLowWarning OCTET STRING,
--                 bladeVRM1VoltHighWarning OCTET STRING,
--                 bladeVRM1VoltLowWarning OCTET STRING,
                   bladeVoltThresholdSensorCapability INTEGER,
                   bladeSensor1VoltHighWarning OCTET STRING,
                   bladeSensor1VoltLowWarning OCTET STRING,
                   bladeSensor2VoltHighWarning OCTET STRING,
                   bladeSensor2VoltLowWarning OCTET STRING,
                   bladeSensor3VoltHighWarning OCTET STRING,
                   bladeSensor3VoltLowWarning OCTET STRING,
                   bladeSensor4VoltHighWarning OCTET STRING,
                   bladeSensor4VoltLowWarning OCTET STRING,
                   bladeSensor5VoltHighWarning OCTET STRING,
                   bladeSensor5VoltLowWarning OCTET STRING,
                   bladeSensor6VoltHighWarning OCTET STRING,
                   bladeSensor6VoltLowWarning OCTET STRING,
                   bladeSensor7VoltHighWarning OCTET STRING,
                   bladeSensor7VoltLowWarning OCTET STRING,
                   bladeSensor8VoltHighWarning OCTET STRING,
                   bladeSensor8VoltLowWarning OCTET STRING,
                   bladeSensor9VoltHighWarning OCTET STRING,
                   bladeSensor9VoltLowWarning OCTET STRING,
                   bladeSensor10VoltHighWarning OCTET STRING,
                   bladeSensor10VoltLowWarning OCTET STRING,
                   bladeSensor11VoltHighWarning OCTET STRING,
                   bladeSensor11VoltLowWarning OCTET STRING,
                   bladeSensor12VoltHighWarning OCTET STRING,
                   bladeSensor12VoltLowWarning OCTET STRING,
                   bladeSensor13VoltHighWarning OCTET STRING,
                   bladeSensor13VoltLowWarning OCTET STRING,
                   bladeSensor14VoltHighWarning OCTET STRING,
                   bladeSensor14VoltLowWarning OCTET STRING,
                   bladeSensor15VoltHighWarning OCTET STRING,
                   bladeSensor15VoltLowWarning OCTET STRING,
                   bladeSensor16VoltHighWarning OCTET STRING,
                   bladeSensor16VoltLowWarning OCTET STRING,
                   bladeSensor17VoltHighWarning OCTET STRING,
                   bladeSensor17VoltLowWarning OCTET STRING,
                   bladeSensor18VoltHighWarning OCTET STRING,
                   bladeSensor18VoltLowWarning OCTET STRING,
                   bladeSensor19VoltHighWarning OCTET STRING,
                   bladeSensor19VoltLowWarning OCTET STRING,
                   bladeSensor20VoltHighWarning OCTET STRING,
                   bladeSensor20VoltLowWarning OCTET STRING,
                   bladeSensor21VoltHighWarning OCTET STRING,
                   bladeSensor21VoltLowWarning OCTET STRING,
                   bladeSensor22VoltHighWarning OCTET STRING,
                   bladeSensor22VoltLowWarning OCTET STRING,
                   bladeSensor23VoltHighWarning OCTET STRING,
                   bladeSensor23VoltLowWarning OCTET STRING,
                   bladeSensor24VoltHighWarning OCTET STRING,
                   bladeSensor24VoltLowWarning OCTET STRING,
                   bladeSensor25VoltHighWarning OCTET STRING,
                   bladeSensor25VoltLowWarning OCTET STRING,
                   bladeSensor26VoltHighWarning OCTET STRING,
                   bladeSensor26VoltLowWarning OCTET STRING,
                   bladeSensor27VoltHighWarning OCTET STRING,
                   bladeSensor27VoltLowWarning OCTET STRING,
                   bladeSensor28VoltHighWarning OCTET STRING,
                   bladeSensor28VoltLowWarning OCTET STRING,
                   bladeSensor29VoltHighWarning OCTET STRING,
                   bladeSensor29VoltLowWarning OCTET STRING,
                   bladeSensor30VoltHighWarning OCTET STRING,
                   bladeSensor30VoltLowWarning OCTET STRING
       }

       voltageThresholdIndex  OBJECT-TYPE
                   SYNTAX  INTEGER
                   ACCESS  read-only
                   STATUS  mandatory
                   DESCRIPTION
                   "Blade voltage thresholds table index."
                   ::= { bladeVoltageThresholdsEntry 1 }


       voltageThresholdBladeId  OBJECT-TYPE
                   SYNTAX  INTEGER {
--                      managementModule(0),
                     blade1(1),
                     blade2(2),
                     blade3(3),
                     blade4(4),
                     blade5(5),
                     blade6(6),
                     blade7(7),
                     blade8(8),
                     blade9(9),
                     blade10(10),
                     blade11(11),
                     blade12(12),
                     blade13(13),
                     blade14(14)
                   }
                   ACCESS  read-only
                   STATUS  mandatory
                   DESCRIPTION
                   "The numeric blade ID."
                   ::= { bladeVoltageThresholdsEntry 2 }

       voltageThresholdBladeExists OBJECT-TYPE
                   SYNTAX  INTEGER {
                     false(0),
                     true(1)
                   }
                   ACCESS  read-only
                   STATUS  mandatory
                   DESCRIPTION
                   "Indicates whether the server blade specified exists or not."
                   ::= { bladeVoltageThresholdsEntry 3 }

       voltageThresholdBladePowerState OBJECT-TYPE
                   SYNTAX  INTEGER {
                     off(0),
                     on(1)
                   }
                   ACCESS  read-only
                   STATUS  mandatory
                   DESCRIPTION
                   "Indicates whether the server blade specified is powered on or not."
                   ::= { bladeVoltageThresholdsEntry 4 }

       voltageThresholdBladeName OBJECT-TYPE
                   SYNTAX  OCTET STRING
                   ACCESS  read-write
                   STATUS  mandatory
                   DESCRIPTION
                   "The name of the blade as a null terminated string."
                   ::= { bladeVoltageThresholdsEntry 5 }

       bladePlus5VoltHighWarning OBJECT-TYPE
                   SYNTAX  OCTET STRING
                   ACCESS  read-only
                   STATUS  mandatory
                   DESCRIPTION
                   "Voltage warning threshold reading expressed in Volts(V).
                   If the voltage rises above this value a warning alert/event
                   if enabled will be generated.
                   An octet string expressed as 'sdd.dd Volts' where:
                   s is the sign ('-' for negative or '+' for positive)
                   d is a decimal digit or blank space for a leading zero.
                   The string 'Not Readable!' indicates that the given monitor
                   is not supported on this system.
                   The string 'No Voltage' indicates that the given monitor
                   does not exist on this system or is powered off."
                   ::= { bladeVoltageThresholdsEntry 6 }

       bladePlus5VoltLowWarning OBJECT-TYPE
                   SYNTAX  OCTET STRING
                   ACCESS  read-only
                   STATUS  mandatory
                   DESCRIPTION
                   "Voltage warning threshold reading expressed in Volts(V).
                   If the voltage drops below this value a warning alert/event
                   if enabled will be generated.
                   An octet string expressed as 'sdd.dd Volts' where:
                   s is the sign ('-' for negative or '+' for positive)
                   d is a decimal digit or blank space for a leading zero.
                   The string 'Not Readable!' indicates that the given monitor
                   is not supported on this system.
                   The string 'No Voltage' indicates that the given monitor
                   does not exist on this system or is powered off."
                   ::= { bladeVoltageThresholdsEntry 7 }

       bladePlus3pt3VoltHighWarning OBJECT-TYPE
                   SYNTAX  OCTET STRING
                   ACCESS  read-only
                   STATUS  mandatory
                   DESCRIPTION
                   "Voltage warning threshold reading expressed in Volts(V).
                   If the voltage rises above this value a warning alert/event
                   if enabled will be generated.
                   An octet string expressed as 'sdd.dd Volts' where:
                   s is the sign ('-' for negative or '+' for positive)
                   d is a decimal digit or blank space for a leading zero.
                   The string 'Not Readable!' indicates that the given monitor
                   is not supported on this system.
                   The string 'No Voltage' indicates that the given monitor
                   does not exist on this system or is powered off."
                   ::= { bladeVoltageThresholdsEntry 8 }

       bladePlus3pt3VoltLowWarning OBJECT-TYPE
                   SYNTAX  OCTET STRING
                   ACCESS  read-only
                   STATUS  mandatory
                   DESCRIPTION
                   "Voltage warning threshold reading expressed in Volts(V).
                   If the voltage drops below this value a warning alert/event
                   if enabled will be generated.
                   An octet string expressed as 'sdd.dd Volts' where:
                   s is the sign ('-' for negative or '+' for positive)
                   d is a decimal digit or blank space for a leading zero.
                   The string 'Not Readable!' indicates that the given monitor
                   is not supported on this system.
                   The string 'No Voltage' indicates that the given monitor
                   does not exist on this system or is powered off."
                   ::= { bladeVoltageThresholdsEntry 9 }

       bladePlus12VoltHighWarning OBJECT-TYPE
                   SYNTAX  OCTET STRING
                   ACCESS  read-only
                   STATUS  mandatory
                   DESCRIPTION
                   "Voltage warning threshold reading expressed in Volts(V).
                   If the voltage rises above this value a warning alert/event
                   if enabled will be generated.
                   An octet string expressed as 'sdd.dd Volts' where:
                   s is the sign ('-' for negative or '+' for positive)
                   d is a decimal digit or blank space for a leading zero.
                   The string 'Not Readable!' indicates that the given monitor
                   is not supported on this system.
                   The string 'No Voltage' indicates that the given monitor
                   does not exist on this system or is powered off."
                   ::= { bladeVoltageThresholdsEntry 10 }

       bladePlus12VoltLowWarning OBJECT-TYPE
                   SYNTAX  OCTET STRING
                   ACCESS  read-only
                   STATUS  mandatory
                   DESCRIPTION
                   "Voltage warning threshold reading expressed in Volts(V).
                   If the voltage drops below this value a warning alert/event
                   if enabled will be generated.
                   An octet string expressed as 'sdd.dd Volts' where:
                   s is the sign ('-' for negative or '+' for positive)
                   d is a decimal digit or blank space for a leading zero.
                   The string 'Not Readable!' indicates that the given monitor
                   is not supported on this system.
                   The string 'No Voltage' indicates that the given monitor
                   does not exist on this system or is powered off."
                   ::= { bladeVoltageThresholdsEntry 11 }

--     bladeMinus12VoltHighWarning OBJECT-TYPE
--                 SYNTAX  OCTET STRING
--                 ACCESS  read-only
--                 STATUS  mandatory
--                 DESCRIPTION
--                 "Voltage warning threshold reading expressed in Volts(V).
--                 If the voltage rises above this value a warning alert/event
--                 if enabled will be generated.
--                 An octet string expressed as 'sdd.dd Volts' where:
--                 s is the sign ('-' for negative or '+' for positive)
--                 d is a decimal digit or blank space for a leading zero.
--                 The string 'Not Readable!' indicates that the given monitor
--                 is not supported on this system."
--                 ::= { bladeVoltageThresholdsEntry 12 }
--
--     bladeMinus12VoltLowWarning OBJECT-TYPE
--                 SYNTAX  OCTET STRING
--                 ACCESS  read-only
--                 STATUS  mandatory
--                 DESCRIPTION
--                 "Voltage warning threshold reading expressed in Volts(V).
--                 If the voltage drops below this value a warning alert/event
--                 if enabled will be generated.
--                 An octet string expressed as 'sdd.dd Volts' where:
--                 s is the sign ('-' for negative or '+' for positive)
--                 d is a decimal digit or blank space for a leading zero.
--                 The string 'Not Readable!' indicates that the given monitor
--                 is not supported on this system."
--                 ::= { bladeVoltageThresholdsEntry 13 }

       bladePlus2pt5VoltHighWarning OBJECT-TYPE
                   SYNTAX  OCTET STRING
                   ACCESS  read-only
                   STATUS  mandatory
                   DESCRIPTION
                   "Voltage warning threshold reading expressed in Volts(V).
                   If the voltage rises above this value a warning alert/event
                   if enabled will be generated.
                   An octet string expressed as 'sdd.dd Volts' where:
                   s is the sign ('-' for negative or '+' for positive)
                   d is a decimal digit or blank space for a leading zero.
                   The string 'Not Readable!' indicates that the given monitor
                   is not supported on this system.
                   The string 'No Voltage' indicates that the given monitor
                   does not exist on this system or is powered off."
                   ::= { bladeVoltageThresholdsEntry 14 }

       bladePlus2pt5VoltLowWarning OBJECT-TYPE
                   SYNTAX  OCTET STRING
                   ACCESS  read-only
                   STATUS  mandatory
                   DESCRIPTION
                   "Voltage warning threshold reading expressed in Volts(V).
                   If the voltage drops below this value a warning alert/event
                   if enabled will be generated.
                   An octet string expressed as 'sdd.dd Volts' where:
                   s is the sign ('-' for negative or '+' for positive)
                   d is a decimal digit or blank space for a leading zero.
                   The string 'Not Readable!' indicates that the given monitor
                   is not supported on this system.
                   The string 'No Voltage' indicates that the given monitor
                   does not exist on this system or is powered off."
                   ::= { bladeVoltageThresholdsEntry 15 }

       bladePlus1pt5VoltHighWarning OBJECT-TYPE
                   SYNTAX  OCTET STRING
                   ACCESS  read-only
                   STATUS  mandatory
                   DESCRIPTION
                   "Voltage warning threshold reading expressed in Volts(V).
                   If the voltage rises above this value a warning alert/event
                   if enabled will be generated.
                   An octet string expressed as 'sdd.dd Volts' where:
                   s is the sign ('-' for negative or '+' for positive)
                   d is a decimal digit or blank space for a leading zero.
                   The string 'Not Readable!' indicates that the given monitor
                   is not supported on this system.
                   The string 'No Voltage' indicates that the given monitor
                   does not exist on this system or is powered off."
                   ::= { bladeVoltageThresholdsEntry 16 }

       bladePlus1pt5VoltLowWarning OBJECT-TYPE
                   SYNTAX  OCTET STRING
                   ACCESS  read-only
                   STATUS  mandatory
                   DESCRIPTION
                   "Voltage warning threshold reading expressed in Volts(V).
                   If the voltage drops below this value a warning alert/event
                   if enabled will be generated.
                   An octet string expressed as 'sdd.dd Volts' where:
                   s is the sign ('-' for negative or '+' for positive)
                   d is a decimal digit or blank space for a leading zero.
                   The string 'Not Readable!' indicates that the given monitor
                   is not supported on this system.
                   The string 'No Voltage' indicates that the given monitor
                   does not exist on this system or is powered off."
                   ::= { bladeVoltageThresholdsEntry 17 }

       bladePlus1pt25VoltHighWarning OBJECT-TYPE
                   SYNTAX  OCTET STRING
                   ACCESS  read-only
                   STATUS  mandatory
                   DESCRIPTION
                   "Voltage warning threshold reading expressed in Volts(V).
                   If the voltage rises above this value a warning alert/event
                   if enabled will be generated.
                   An octet string expressed as 'sdd.dd Volts' where:
                   s is the sign ('-' for negative or '+' for positive)
                   d is a decimal digit or blank space for a leading zero.
                   The string 'Not Readable!' indicates that the given monitor
                   is not supported on this system.
                   The string 'No Voltage' indicates that the given monitor
                   does not exist on this system or is powered off."
                   ::= { bladeVoltageThresholdsEntry 18 }

       bladePlus1pt25VoltLowWarning OBJECT-TYPE
                   SYNTAX  OCTET STRING
                   ACCESS  read-only
                   STATUS  mandatory
                   DESCRIPTION
                   "Voltage warning threshold reading expressed in Volts(V).
                   If the voltage drops below this value a warning alert/event
                   if enabled will be generated.
                   An octet string expressed as 'sdd.dd Volts' where:
                   s is the sign ('-' for negative or '+' for positive)
                   d is a decimal digit or blank space for a leading zero.
                   The string 'Not Readable!' indicates that the given monitor
                   is not supported on this system.
                   The string 'No Voltage' indicates that the given monitor
                   does not exist on this system or is powered off."
                   ::= { bladeVoltageThresholdsEntry 19 }

--     bladeVRM1VoltHighWarning OBJECT-TYPE
--                 SYNTAX  OCTET STRING
--                 ACCESS  read-only
--                 STATUS  mandatory
--                 DESCRIPTION
--                 "The value for the VRM1 voltage."
--                 "Voltage warning threshold reading expressed in Volts(V).
--                 If the voltage rises above this value a warning alert/event
--                 if enabled will be generated.
--                 An octet string expressed as 'sdd.dd Volts' where:
--                 s is the sign ('-' for negative or '+' for positive)
--                 d is a decimal digit or blank space for a leading zero.
--                 The string 'Not Readable!' indicates that the given monitor
--                 is not supported on this system."
--                 ::= { bladeVoltageThresholdsEntry 20 }
--
--     bladeVRM1VoltLowWarning OBJECT-TYPE
--                 SYNTAX  OCTET STRING
--                 ACCESS  read-only
--                 STATUS  mandatory
--                 DESCRIPTION
--                 "The value for the VRM1 voltage."
--                 "Voltage warning threshold reading expressed in Volts(V).
--                 If the voltage drops below this value a warning alert/event
--                 if enabled will be generated.
--                 An octet string expressed as 'sdd.dd Volts' where:
--                 s is the sign ('-' for negative or '+' for positive)
--                 d is a decimal digit or blank space for a leading zero.
--                 The string 'Not Readable!' indicates that the given monitor
--                 is not supported on this system."
--                 ::= { bladeVoltageThresholdsEntry 21 }

       bladeVoltThresholdSensorCapability OBJECT-TYPE
                   SYNTAX  INTEGER {
                     false(0),
                     true(1)
                   }
                   ACCESS  read-only
                   STATUS  mandatory
                   DESCRIPTION
                   "Indicates whether the server blade is IPMI capable or not."
                   ::= { bladeVoltageThresholdsEntry 22 }

       bladeSensor1VoltHighWarning OBJECT-TYPE
                   SYNTAX  OCTET STRING
                   ACCESS  read-only
                   STATUS  mandatory
                   DESCRIPTION
                   "Voltage warning threshold reading for IPMI blades expressed in Volts(V).
                   If the voltage rises above this value a warning alert/event
                   if enabled will be generated.
                   An octet string expressed as 'sdd.dd Volts' where:
                   s is the sign ('-' for negative or '+' for positive)
                   d is a decimal digit or blank space for a leading zero.
                   The string 'Not Readable!' indicates that the given monitor
                   is not supported on this system.
                   The string 'No Voltage' indicates that the given monitor
                   does not exist on this system or is powered off."
                   ::= { bladeVoltageThresholdsEntry 23 }

       bladeSensor1VoltLowWarning OBJECT-TYPE
                   SYNTAX  OCTET STRING
                   ACCESS  read-only
                   STATUS  mandatory
                   DESCRIPTION
                   "Voltage warning threshold reading for IPMI blades expressed in Volts(V).
                   If the voltage drops below this value a warning alert/event
                   if enabled will be generated.
                   An octet string expressed as 'sdd.dd Volts' where:
                   s is the sign ('-' for negative or '+' for positive)
                   d is a decimal digit or blank space for a leading zero.
                   The string 'Not Readable!' indicates that the given monitor
                   is not supported on this system.
                   The string 'No Voltage' indicates that the given monitor
                   does not exist on this system or is powered off."
                   ::= { bladeVoltageThresholdsEntry 24 }

       bladeSensor2VoltHighWarning OBJECT-TYPE
                   SYNTAX  OCTET STRING
                   ACCESS  read-only
                   STATUS  mandatory
                   DESCRIPTION
                   "Voltage warning threshold reading for IPMI blades expressed in Volts(V).
                   If the voltage rises above this value a warning alert/event
                   if enabled will be generated.
                   An octet string expressed as 'sdd.dd Volts' where:
                   s is the sign ('-' for negative or '+' for positive)
                   d is a decimal digit or blank space for a leading zero.
                   The string 'Not Readable!' indicates that the given monitor
                   is not supported on this system.
                   The string 'No Voltage' indicates that the given monitor
                   does not exist on this system or is powered off."
                   ::= { bladeVoltageThresholdsEntry 25 }

       bladeSensor2VoltLowWarning OBJECT-TYPE
                   SYNTAX  OCTET STRING
                   ACCESS  read-only
                   STATUS  mandatory
                   DESCRIPTION
                   "Voltage warning threshold reading for IPMI blades expressed in Volts(V).
                   If the voltage drops below this value a warning alert/event
                   if enabled will be generated.
                   An octet string expressed as 'sdd.dd Volts' where:
                   s is the sign ('-' for negative or '+' for positive)
                   d is a decimal digit or blank space for a leading zero.
                   The string 'Not Readable!' indicates that the given monitor
                   is not supported on this system.
                   The string 'No Voltage' indicates that the given monitor
                   does not exist on this system or is powered off."
                   ::= { bladeVoltageThresholdsEntry 26 }

       bladeSensor3VoltHighWarning OBJECT-TYPE
                   SYNTAX  OCTET STRING
                   ACCESS  read-only
                   STATUS  mandatory
                   DESCRIPTION
                   "Voltage warning threshold reading for IPMI blades expressed in Volts(V).
                   If the voltage rises above this value a warning alert/event
                   if enabled will be generated.
                   An octet string expressed as 'sdd.dd Volts' where:
                   s is the sign ('-' for negative or '+' for positive)
                   d is a decimal digit or blank space for a leading zero.
                   The string 'Not Readable!' indicates that the given monitor
                   is not supported on this system.
                   The string 'No Voltage' indicates that the given monitor
                   does not exist on this system or is powered off."
                   ::= { bladeVoltageThresholdsEntry 27 }

       bladeSensor3VoltLowWarning OBJECT-TYPE
                   SYNTAX  OCTET STRING
                   ACCESS  read-only
                   STATUS  mandatory
                   DESCRIPTION
                   "Voltage warning threshold reading for IPMI blades expressed in Volts(V).
                   If the voltage drops below this value a warning alert/event
                   if enabled will be generated.
                   An octet string expressed as 'sdd.dd Volts' where:
                   s is the sign ('-' for negative or '+' for positive)
                   d is a decimal digit or blank space for a leading zero.
                   The string 'Not Readable!' indicates that the given monitor
                   is not supported on this system.
                   The string 'No Voltage' indicates that the given monitor
                   does not exist on this system or is powered off."
                   ::= { bladeVoltageThresholdsEntry 28 }

       bladeSensor4VoltHighWarning OBJECT-TYPE
                   SYNTAX  OCTET STRING
                   ACCESS  read-only
                   STATUS  mandatory
                   DESCRIPTION
                   "Voltage warning threshold reading for IPMI blades expressed in Volts(V).
                   If the voltage rises above this value a warning alert/event
                   if enabled will be generated.
                   An octet string expressed as 'sdd.dd Volts' where:
                   s is the sign ('-' for negative or '+' for positive)
                   d is a decimal digit or blank space for a leading zero.
                   The string 'Not Readable!' indicates that the given monitor
                   is not supported on this system.
                   The string 'No Voltage' indicates that the given monitor
                   does not exist on this system or is powered off."
                   ::= { bladeVoltageThresholdsEntry 29 }

       bladeSensor4VoltLowWarning OBJECT-TYPE
                   SYNTAX  OCTET STRING
                   ACCESS  read-only
                   STATUS  mandatory
                   DESCRIPTION
                   "Voltage warning threshold reading for IPMI blades expressed in Volts(V).
                   If the voltage drops below this value a warning alert/event
                   if enabled will be generated.
                   An octet string expressed as 'sdd.dd Volts' where:
                   s is the sign ('-' for negative or '+' for positive)
                   d is a decimal digit or blank space for a leading zero.
                   The string 'Not Readable!' indicates that the given monitor
                   is not supported on this system.
                   The string 'No Voltage' indicates that the given monitor
                   does not exist on this system or is powered off."
                   ::= { bladeVoltageThresholdsEntry 30 }

       bladeSensor5VoltHighWarning OBJECT-TYPE
                   SYNTAX  OCTET STRING
                   ACCESS  read-only
                   STATUS  mandatory
                   DESCRIPTION
                   "Voltage warning threshold reading for IPMI blades expressed in Volts(V).
                   If the voltage rises above this value a warning alert/event
                   if enabled will be generated.
                   An octet string expressed as 'sdd.dd Volts' where:
                   s is the sign ('-' for negative or '+' for positive)
                   d is a decimal digit or blank space for a leading zero.
                   The string 'Not Readable!' indicates that the given monitor
                   is not supported on this system.
                   The string 'No Voltage' indicates that the given monitor
                   does not exist on this system or is powered off."
                   ::= { bladeVoltageThresholdsEntry 31 }

       bladeSensor5VoltLowWarning OBJECT-TYPE
                   SYNTAX  OCTET STRING
                   ACCESS  read-only
                   STATUS  mandatory
                   DESCRIPTION
                   "Voltage warning threshold reading for IPMI blades expressed in Volts(V).
                   If the voltage drops below this value a warning alert/event
                   if enabled will be generated.
                   An octet string expressed as 'sdd.dd Volts' where:
                   s is the sign ('-' for negative or '+' for positive)
                   d is a decimal digit or blank space for a leading zero.
                   The string 'Not Readable!' indicates that the given monitor
                   is not supported on this system.
                   The string 'No Voltage' indicates that the given monitor
                   does not exist on this system or is powered off."
                   ::= { bladeVoltageThresholdsEntry 32 }

       bladeSensor6VoltHighWarning OBJECT-TYPE
                   SYNTAX  OCTET STRING
                   ACCESS  read-only
                   STATUS  mandatory
                   DESCRIPTION
                   "Voltage warning threshold reading for IPMI blades expressed in Volts(V).
                   If the voltage rises above this value a warning alert/event
                   if enabled will be generated.
                   An octet string expressed as 'sdd.dd Volts' where:
                   s is the sign ('-' for negative or '+' for positive)
                   d is a decimal digit or blank space for a leading zero.
                   The string 'Not Readable!' indicates that the given monitor
                   is not supported on this system.
                   The string 'No Voltage' indicates that the given monitor
                   does not exist on this system or is powered off."
                   ::= { bladeVoltageThresholdsEntry 33 }

       bladeSensor6VoltLowWarning OBJECT-TYPE
                   SYNTAX  OCTET STRING
                   ACCESS  read-only
                   STATUS  mandatory
                   DESCRIPTION
                   "Voltage warning threshold reading for IPMI blades expressed in Volts(V).
                   If the voltage drops below this value a warning alert/event
                   if enabled will be generated.
                   An octet string expressed as 'sdd.dd Volts' where:
                   s is the sign ('-' for negative or '+' for positive)
                   d is a decimal digit or blank space for a leading zero.
                   The string 'Not Readable!' indicates that the given monitor
                   is not supported on this system.
                   The string 'No Voltage' indicates that the given monitor
                   does not exist on this system or is powered off."
                   ::= { bladeVoltageThresholdsEntry 34 }

       bladeSensor7VoltHighWarning OBJECT-TYPE
                   SYNTAX  OCTET STRING
                   ACCESS  read-only
                   STATUS  mandatory
                   DESCRIPTION
                   "Voltage warning threshold reading for IPMI blades expressed in Volts(V).
                   If the voltage rises above this value a warning alert/event
                   if enabled will be generated.
                   An octet string expressed as 'sdd.dd Volts' where:
                   s is the sign ('-' for negative or '+' for positive)
                   d is a decimal digit or blank space for a leading zero.
                   The string 'Not Readable!' indicates that the given monitor
                   is not supported on this system.
                   The string 'No Voltage' indicates that the given monitor
                   does not exist on this system or is powered off."
                   ::= { bladeVoltageThresholdsEntry 35 }

       bladeSensor7VoltLowWarning OBJECT-TYPE
                   SYNTAX  OCTET STRING
                   ACCESS  read-only
                   STATUS  mandatory
                   DESCRIPTION
                   "Voltage warning threshold reading for IPMI blades expressed in Volts(V).
                   If the voltage drops below this value a warning alert/event
                   if enabled will be generated.
                   An octet string expressed as 'sdd.dd Volts' where:
                   s is the sign ('-' for negative or '+' for positive)
                   d is a decimal digit or blank space for a leading zero.
                   The string 'Not Readable!' indicates that the given monitor
                   is not supported on this system.
                   The string 'No Voltage' indicates that the given monitor
                   does not exist on this system or is powered off."
                   ::= { bladeVoltageThresholdsEntry 36 }

       bladeSensor8VoltHighWarning OBJECT-TYPE
                   SYNTAX  OCTET STRING
                   ACCESS  read-only
                   STATUS  mandatory
                   DESCRIPTION
                   "Voltage warning threshold reading for IPMI blades expressed in Volts(V).
                   If the voltage rises above this value a warning alert/event
                   if enabled will be generated.
                   An octet string expressed as 'sdd.dd Volts' where:
                   s is the sign ('-' for negative or '+' for positive)
                   d is a decimal digit or blank space for a leading zero.
                   The string 'Not Readable!' indicates that the given monitor
                   is not supported on this system.
                   The string 'No Voltage' indicates that the given monitor
                   does not exist on this system or is powered off."
                   ::= { bladeVoltageThresholdsEntry 37 }

       bladeSensor8VoltLowWarning OBJECT-TYPE
                   SYNTAX  OCTET STRING
                   ACCESS  read-only
                   STATUS  mandatory
                   DESCRIPTION
                   "Voltage warning threshold reading for IPMI blades expressed in Volts(V).
                   If the voltage drops below this value a warning alert/event
                   if enabled will be generated.
                   An octet string expressed as 'sdd.dd Volts' where:
                   s is the sign ('-' for negative or '+' for positive)
                   d is a decimal digit or blank space for a leading zero.
                   The string 'Not Readable!' indicates that the given monitor
                   is not supported on this system.
                   The string 'No Voltage' indicates that the given monitor
                   does not exist on this system or is powered off."
                   ::= { bladeVoltageThresholdsEntry 38 }

       bladeSensor9VoltHighWarning OBJECT-TYPE
                   SYNTAX  OCTET STRING
                   ACCESS  read-only
                   STATUS  mandatory
                   DESCRIPTION
                   "Voltage warning threshold reading for IPMI blades expressed in Volts(V).
                   If the voltage rises above this value a warning alert/event
                   if enabled will be generated.
                   An octet string expressed as 'sdd.dd Volts' where:
                   s is the sign ('-' for negative or '+' for positive)
                   d is a decimal digit or blank space for a leading zero.
                   The string 'Not Readable!' indicates that the given monitor
                   is not supported on this system.
                   The string 'No Voltage' indicates that the given monitor
                   does not exist on this system or is powered off."
                   ::= { bladeVoltageThresholdsEntry 39 }

       bladeSensor9VoltLowWarning OBJECT-TYPE
                   SYNTAX  OCTET STRING
                   ACCESS  read-only
                   STATUS  mandatory
                   DESCRIPTION
                   "Voltage warning threshold reading for IPMI blades expressed in Volts(V).
                   If the voltage drops below this value a warning alert/event
                   if enabled will be generated.
                   An octet string expressed as 'sdd.dd Volts' where:
                   s is the sign ('-' for negative or '+' for positive)
                   d is a decimal digit or blank space for a leading zero.
                   The string 'Not Readable!' indicates that the given monitor
                   is not supported on this system.
                   The string 'No Voltage' indicates that the given monitor
                   does not exist on this system or is powered off."
                   ::= { bladeVoltageThresholdsEntry 40 }

       bladeSensor10VoltHighWarning OBJECT-TYPE
                   SYNTAX  OCTET STRING
                   ACCESS  read-only
                   STATUS  mandatory
                   DESCRIPTION
                   "Voltage warning threshold reading for IPMI blades expressed in Volts(V).
                   If the voltage rises above this value a warning alert/event
                   if enabled will be generated.
                   An octet string expressed as 'sdd.dd Volts' where:
                   s is the sign ('-' for negative or '+' for positive)
                   d is a decimal digit or blank space for a leading zero.
                   The string 'Not Readable!' indicates that the given monitor
                   is not supported on this system.
                   The string 'No Voltage' indicates that the given monitor
                   does not exist on this system or is powered off."
                   ::= { bladeVoltageThresholdsEntry 41 }

       bladeSensor10VoltLowWarning OBJECT-TYPE
                   SYNTAX  OCTET STRING
                   ACCESS  read-only
                   STATUS  mandatory
                   DESCRIPTION
                   "Voltage warning threshold reading for IPMI blades expressed in Volts(V).
                   If the voltage drops below this value a warning alert/event
                   if enabled will be generated.
                   An octet string expressed as 'sdd.dd Volts' where:
                   s is the sign ('-' for negative or '+' for positive)
                   d is a decimal digit or blank space for a leading zero.
                   The string 'Not Readable!' indicates that the given monitor
                   is not supported on this system.
                   The string 'No Voltage' indicates that the given monitor
                   does not exist on this system or is powered off."
                   ::= { bladeVoltageThresholdsEntry 42 }

       bladeSensor11VoltHighWarning OBJECT-TYPE
                   SYNTAX  OCTET STRING
                   ACCESS  read-only
                   STATUS  mandatory
                   DESCRIPTION
                   "Voltage warning threshold reading for IPMI blades expressed in Volts(V).
                   If the voltage rises above this value a warning alert/event
                   if enabled will be generated.
                   An octet string expressed as 'sdd.dd Volts' where:
                   s is the sign ('-' for negative or '+' for positive)
                   d is a decimal digit or blank space for a leading zero.
                   The string 'Not Readable!' indicates that the given monitor
                   is not supported on this system.
                   The string 'No Voltage' indicates that the given monitor
                   does not exist on this system or is powered off."
                   ::= { bladeVoltageThresholdsEntry 43 }

       bladeSensor11VoltLowWarning OBJECT-TYPE
                   SYNTAX  OCTET STRING
                   ACCESS  read-only
                   STATUS  mandatory
                   DESCRIPTION
                   "Voltage warning threshold reading for IPMI blades expressed in Volts(V).
                   If the voltage drops below this value a warning alert/event
                   if enabled will be generated.
                   An octet string expressed as 'sdd.dd Volts' where:
                   s is the sign ('-' for negative or '+' for positive)
                   d is a decimal digit or blank space for a leading zero.
                   The string 'Not Readable!' indicates that the given monitor
                   is not supported on this system.
                   The string 'No Voltage' indicates that the given monitor
                   does not exist on this system or is powered off."
                   ::= { bladeVoltageThresholdsEntry 44 }

       bladeSensor12VoltHighWarning OBJECT-TYPE
                   SYNTAX  OCTET STRING
                   ACCESS  read-only
                   STATUS  mandatory
                   DESCRIPTION
                   "Voltage warning threshold reading for IPMI blades expressed in Volts(V).
                   If the voltage rises above this value a warning alert/event
                   if enabled will be generated.
                   An octet string expressed as 'sdd.dd Volts' where:
                   s is the sign ('-' for negative or '+' for positive)
                   d is a decimal digit or blank space for a leading zero.
                   The string 'Not Readable!' indicates that the given monitor
                   is not supported on this system.
                   The string 'No Voltage' indicates that the given monitor
                   does not exist on this system or is powered off."
                   ::= { bladeVoltageThresholdsEntry 45 }

       bladeSensor12VoltLowWarning OBJECT-TYPE
                   SYNTAX  OCTET STRING
                   ACCESS  read-only
                   STATUS  mandatory
                   DESCRIPTION
                   "Voltage warning threshold reading for IPMI blades expressed in Volts(V).
                   If the voltage drops below this value a warning alert/event
                   if enabled will be generated.
                   An octet string expressed as 'sdd.dd Volts' where:
                   s is the sign ('-' for negative or '+' for positive)
                   d is a decimal digit or blank space for a leading zero.
                   The string 'Not Readable!' indicates that the given monitor
                   is not supported on this system.
                   The string 'No Voltage' indicates that the given monitor
                   does not exist on this system or is powered off."
                   ::= { bladeVoltageThresholdsEntry 46 }

       bladeSensor13VoltHighWarning OBJECT-TYPE
                   SYNTAX  OCTET STRING
                   ACCESS  read-only
                   STATUS  mandatory
                   DESCRIPTION
                   "Voltage warning threshold reading for IPMI blades expressed in Volts(V).
                   If the voltage rises above this value a warning alert/event
                   if enabled will be generated.
                   An octet string expressed as 'sdd.dd Volts' where:
                   s is the sign ('-' for negative or '+' for positive)
                   d is a decimal digit or blank space for a leading zero.
                   The string 'Not Readable!' indicates that the given monitor
                   is not supported on this system.
                   The string 'No Voltage' indicates that the given monitor
                   does not exist on this system or is powered off."
                   ::= { bladeVoltageThresholdsEntry 47 }

       bladeSensor13VoltLowWarning OBJECT-TYPE
                   SYNTAX  OCTET STRING
                   ACCESS  read-only
                   STATUS  mandatory
                   DESCRIPTION
                   "Voltage warning threshold reading for IPMI blades expressed in Volts(V).
                   If the voltage drops below this value a warning alert/event
                   if enabled will be generated.
                   An octet string expressed as 'sdd.dd Volts' where:
                   s is the sign ('-' for negative or '+' for positive)
                   d is a decimal digit or blank space for a leading zero.
                   The string 'Not Readable!' indicates that the given monitor
                   is not supported on this system.
                   The string 'No Voltage' indicates that the given monitor
                   does not exist on this system or is powered off."
                   ::= { bladeVoltageThresholdsEntry 48 }

       bladeSensor14VoltHighWarning OBJECT-TYPE
                   SYNTAX  OCTET STRING
                   ACCESS  read-only
                   STATUS  mandatory
                   DESCRIPTION
                   "Voltage warning threshold reading for IPMI blades expressed in Volts(V).
                   If the voltage rises above this value a warning alert/event
                   if enabled will be generated.
                   An octet string expressed as 'sdd.dd Volts' where:
                   s is the sign ('-' for negative or '+' for positive)
                   d is a decimal digit or blank space for a leading zero.
                   The string 'Not Readable!' indicates that the given monitor
                   is not supported on this system.
                   The string 'No Voltage' indicates that the given monitor
                   does not exist on this system or is powered off."
                   ::= { bladeVoltageThresholdsEntry 49 }

       bladeSensor14VoltLowWarning OBJECT-TYPE
                   SYNTAX  OCTET STRING
                   ACCESS  read-only
                   STATUS  mandatory
                   DESCRIPTION
                   "Voltage warning threshold reading for IPMI blades expressed in Volts(V).
                   If the voltage drops below this value a warning alert/event
                   if enabled will be generated.
                   An octet string expressed as 'sdd.dd Volts' where:
                   s is the sign ('-' for negative or '+' for positive)
                   d is a decimal digit or blank space for a leading zero.
                   The string 'Not Readable!' indicates that the given monitor
                   is not supported on this system.
                   The string 'No Voltage' indicates that the given monitor
                   does not exist on this system or is powered off."
                   ::= { bladeVoltageThresholdsEntry 50 }

       bladeSensor15VoltHighWarning OBJECT-TYPE
                   SYNTAX  OCTET STRING
                   ACCESS  read-only
                   STATUS  mandatory
                   DESCRIPTION
                   "Voltage warning threshold reading for IPMI blades expressed in Volts(V).
                   If the voltage rises above this value a warning alert/event
                   if enabled will be generated.
                   An octet string expressed as 'sdd.dd Volts' where:
                   s is the sign ('-' for negative or '+' for positive)
                   d is a decimal digit or blank space for a leading zero.
                   The string 'Not Readable!' indicates that the given monitor
                   is not supported on this system.
                   The string 'No Voltage' indicates that the given monitor
                   does not exist on this system or is powered off."
                   ::= { bladeVoltageThresholdsEntry 51 }

       bladeSensor15VoltLowWarning OBJECT-TYPE
                   SYNTAX  OCTET STRING
                   ACCESS  read-only
                   STATUS  mandatory
                   DESCRIPTION
                   "Voltage warning threshold reading for IPMI blades expressed in Volts(V).
                   If the voltage drops below this value a warning alert/event
                   if enabled will be generated.
                   An octet string expressed as 'sdd.dd Volts' where:
                   s is the sign ('-' for negative or '+' for positive)
                   d is a decimal digit or blank space for a leading zero.
                   The string 'Not Readable!' indicates that the given monitor
                   is not supported on this system.
                   The string 'No Voltage' indicates that the given monitor
                   does not exist on this system or is powered off."
                   ::= { bladeVoltageThresholdsEntry 52 }

       bladeSensor16VoltHighWarning OBJECT-TYPE
                   SYNTAX  OCTET STRING
                   ACCESS  read-only
                   STATUS  mandatory
                   DESCRIPTION
                   "Voltage warning threshold reading for IPMI blades expressed in Volts(V).
                   If the voltage rises above this value a warning alert/event
                   if enabled will be generated.
                   An octet string expressed as 'sdd.dd Volts' where:
                   s is the sign ('-' for negative or '+' for positive)
                   d is a decimal digit or blank space for a leading zero.
                   The string 'Not Readable!' indicates that the given monitor
                   is not supported on this system.
                   The string 'No Voltage' indicates that the given monitor
                   does not exist on this system or is powered off."
                   ::= { bladeVoltageThresholdsEntry 53 }

       bladeSensor16VoltLowWarning OBJECT-TYPE
                   SYNTAX  OCTET STRING
                   ACCESS  read-only
                   STATUS  mandatory
                   DESCRIPTION
                   "Voltage warning threshold reading for IPMI blades expressed in Volts(V).
                   If the voltage drops below this value a warning alert/event
                   if enabled will be generated.
                   An octet string expressed as 'sdd.dd Volts' where:
                   s is the sign ('-' for negative or '+' for positive)
                   d is a decimal digit or blank space for a leading zero.
                   The string 'Not Readable!' indicates that the given monitor
                   is not supported on this system.
                   The string 'No Voltage' indicates that the given monitor
                   does not exist on this system or is powered off."
                   ::= { bladeVoltageThresholdsEntry 54 }

       bladeSensor17VoltHighWarning OBJECT-TYPE
                   SYNTAX  OCTET STRING
                   ACCESS  read-only
                   STATUS  mandatory
                   DESCRIPTION
                   "Voltage warning threshold reading for IPMI blades expressed in Volts(V).
                   If the voltage rises above this value a warning alert/event
                   if enabled will be generated.
                   An octet string expressed as 'sdd.dd Volts' where:
                   s is the sign ('-' for negative or '+' for positive)
                   d is a decimal digit or blank space for a leading zero.
                   The string 'Not Readable!' indicates that the given monitor
                   is not supported on this system.
                   The string 'No Voltage' indicates that the given monitor
                   does not exist on this system or is powered off."
                   ::= { bladeVoltageThresholdsEntry 55 }

       bladeSensor17VoltLowWarning OBJECT-TYPE
                   SYNTAX  OCTET STRING
                   ACCESS  read-only
                   STATUS  mandatory
                   DESCRIPTION
                   "Voltage warning threshold reading for IPMI blades expressed in Volts(V).
                   If the voltage drops below this value a warning alert/event
                   if enabled will be generated.
                   An octet string expressed as 'sdd.dd Volts' where:
                   s is the sign ('-' for negative or '+' for positive)
                   d is a decimal digit or blank space for a leading zero.
                   The string 'Not Readable!' indicates that the given monitor
                   is not supported on this system.
                   The string 'No Voltage' indicates that the given monitor
                   does not exist on this system or is powered off."
                   ::= { bladeVoltageThresholdsEntry 56 }

       bladeSensor18VoltHighWarning OBJECT-TYPE
                   SYNTAX  OCTET STRING
                   ACCESS  read-only
                   STATUS  mandatory
                   DESCRIPTION
                   "Voltage warning threshold reading for IPMI blades expressed in Volts(V).
                   If the voltage rises above this value a warning alert/event
                   if enabled will be generated.
                   An octet string expressed as 'sdd.dd Volts' where:
                   s is the sign ('-' for negative or '+' for positive)
                   d is a decimal digit or blank space for a leading zero.
                   The string 'Not Readable!' indicates that the given monitor
                   is not supported on this system.
                   The string 'No Voltage' indicates that the given monitor
                   does not exist on this system or is powered off."
                   ::= { bladeVoltageThresholdsEntry 57 }

       bladeSensor18VoltLowWarning OBJECT-TYPE
                   SYNTAX  OCTET STRING
                   ACCESS  read-only
                   STATUS  mandatory
                   DESCRIPTION
                   "Voltage warning threshold reading for IPMI blades expressed in Volts(V).
                   If the voltage drops below this value a warning alert/event
                   if enabled will be generated.
                   An octet string expressed as 'sdd.dd Volts' where:
                   s is the sign ('-' for negative or '+' for positive)
                   d is a decimal digit or blank space for a leading zero.
                   The string 'Not Readable!' indicates that the given monitor
                   is not supported on this system.
                   The string 'No Voltage' indicates that the given monitor
                   does not exist on this system or is powered off."
                   ::= { bladeVoltageThresholdsEntry 58 }

       bladeSensor19VoltHighWarning OBJECT-TYPE
                   SYNTAX  OCTET STRING
                   ACCESS  read-only
                   STATUS  mandatory
                   DESCRIPTION
                   "Voltage warning threshold reading for IPMI blades expressed in Volts(V).
                   If the voltage rises above this value a warning alert/event
                   if enabled will be generated.
                   An octet string expressed as 'sdd.dd Volts' where:
                   s is the sign ('-' for negative or '+' for positive)
                   d is a decimal digit or blank space for a leading zero.
                   The string 'Not Readable!' indicates that the given monitor
                   is not supported on this system.
                   The string 'No Voltage' indicates that the given monitor
                   does not exist on this system or is powered off."
                   ::= { bladeVoltageThresholdsEntry 59 }

       bladeSensor19VoltLowWarning OBJECT-TYPE
                   SYNTAX  OCTET STRING
                   ACCESS  read-only
                   STATUS  mandatory
                   DESCRIPTION
                   "Voltage warning threshold reading for IPMI blades expressed in Volts(V).
                   If the voltage drops below this value a warning alert/event
                   if enabled will be generated.
                   An octet string expressed as 'sdd.dd Volts' where:
                   s is the sign ('-' for negative or '+' for positive)
                   d is a decimal digit or blank space for a leading zero.
                   The string 'Not Readable!' indicates that the given monitor
                   is not supported on this system.
                   The string 'No Voltage' indicates that the given monitor
                   does not exist on this system or is powered off."
                   ::= { bladeVoltageThresholdsEntry 60 }

       bladeSensor20VoltHighWarning OBJECT-TYPE
                   SYNTAX  OCTET STRING
                   ACCESS  read-only
                   STATUS  mandatory
                   DESCRIPTION
                   "Voltage warning threshold reading for IPMI blades expressed in Volts(V).
                   If the voltage rises above this value a warning alert/event
                   if enabled will be generated.
                   An octet string expressed as 'sdd.dd Volts' where:
                   s is the sign ('-' for negative or '+' for positive)
                   d is a decimal digit or blank space for a leading zero.
                   The string 'Not Readable!' indicates that the given monitor
                   is not supported on this system.
                   The string 'No Voltage' indicates that the given monitor
                   does not exist on this system or is powered off."
                   ::= { bladeVoltageThresholdsEntry 61 }

       bladeSensor20VoltLowWarning OBJECT-TYPE
                   SYNTAX  OCTET STRING
                   ACCESS  read-only
                   STATUS  mandatory
                   DESCRIPTION
                   "Voltage warning threshold reading for IPMI blades expressed in Volts(V).
                   If the voltage drops below this value a warning alert/event
                   if enabled will be generated.
                   An octet string expressed as 'sdd.dd Volts' where:
                   s is the sign ('-' for negative or '+' for positive)
                   d is a decimal digit or blank space for a leading zero.
                   The string 'Not Readable!' indicates that the given monitor
                   is not supported on this system.
                   The string 'No Voltage' indicates that the given monitor
                   does not exist on this system or is powered off."
                   ::= { bladeVoltageThresholdsEntry 62 }

       bladeSensor21VoltHighWarning OBJECT-TYPE
                   SYNTAX  OCTET STRING
                   ACCESS  read-only
                   STATUS  mandatory
                   DESCRIPTION
                   "Voltage warning threshold reading for IPMI blades expressed in Volts(V).
                   If the voltage rises above this value a warning alert/event
                   if enabled will be generated.
                   An octet string expressed as 'sdd.dd Volts' where:
                   s is the sign ('-' for negative or '+' for positive)
                   d is a decimal digit or blank space for a leading zero.
                   The string 'Not Readable!' indicates that the given monitor
                   is not supported on this system.
                   The string 'No Voltage' indicates that the given monitor
                   does not exist on this system or is powered off."
                   ::= { bladeVoltageThresholdsEntry 63 }

       bladeSensor21VoltLowWarning OBJECT-TYPE
                   SYNTAX  OCTET STRING
                   ACCESS  read-only
                   STATUS  mandatory
                   DESCRIPTION
                   "Voltage warning threshold reading for IPMI blades expressed in Volts(V).
                   If the voltage drops below this value a warning alert/event
                   if enabled will be generated.
                   An octet string expressed as 'sdd.dd Volts' where:
                   s is the sign ('-' for negative or '+' for positive)
                   d is a decimal digit or blank space for a leading zero.
                   The string 'Not Readable!' indicates that the given monitor
                   is not supported on this system.
                   The string 'No Voltage' indicates that the given monitor
                   does not exist on this system or is powered off."
                   ::= { bladeVoltageThresholdsEntry 64 }
                   
       bladeSensor22VoltHighWarning OBJECT-TYPE
                   SYNTAX  OCTET STRING
                   ACCESS  read-only
                   STATUS  mandatory
                   DESCRIPTION
                   "Voltage warning threshold reading for IPMI blades expressed in Volts(V).
                   If the voltage rises above this value a warning alert/event
                   if enabled will be generated.
                   An octet string expressed as 'sdd.dd Volts' where:
                   s is the sign ('-' for negative or '+' for positive)
                   d is a decimal digit or blank space for a leading zero.
                   The string 'Not Readable!' indicates that the given monitor
                   is not supported on this system.
                   The string 'No Voltage' indicates that the given monitor
                   does not exist on this system or is powered off."
                   ::= { bladeVoltageThresholdsEntry 65 }

       bladeSensor22VoltLowWarning OBJECT-TYPE
                   SYNTAX  OCTET STRING
                   ACCESS  read-only
                   STATUS  mandatory
                   DESCRIPTION
                   "Voltage warning threshold reading for IPMI blades expressed in Volts(V).
                   If the voltage drops below this value a warning alert/event
                   if enabled will be generated.
                   An octet string expressed as 'sdd.dd Volts' where:
                   s is the sign ('-' for negative or '+' for positive)
                   d is a decimal digit or blank space for a leading zero.
                   The string 'Not Readable!' indicates that the given monitor
                   is not supported on this system.
                   The string 'No Voltage' indicates that the given monitor
                   does not exist on this system or is powered off."
                   ::= { bladeVoltageThresholdsEntry 66 }

       bladeSensor23VoltHighWarning OBJECT-TYPE
                   SYNTAX  OCTET STRING
                   ACCESS  read-only
                   STATUS  mandatory
                   DESCRIPTION
                   "Voltage warning threshold reading for IPMI blades expressed in Volts(V).
                   If the voltage rises above this value a warning alert/event
                   if enabled will be generated.
                   An octet string expressed as 'sdd.dd Volts' where:
                   s is the sign ('-' for negative or '+' for positive)
                   d is a decimal digit or blank space for a leading zero.
                   The string 'Not Readable!' indicates that the given monitor
                   is not supported on this system.
                   The string 'No Voltage' indicates that the given monitor
                   does not exist on this system or is powered off."
                   ::= { bladeVoltageThresholdsEntry 67 }

       bladeSensor23VoltLowWarning OBJECT-TYPE
                   SYNTAX  OCTET STRING
                   ACCESS  read-only
                   STATUS  mandatory
                   DESCRIPTION
                   "Voltage warning threshold reading for IPMI blades expressed in Volts(V).
                   If the voltage drops below this value a warning alert/event
                   if enabled will be generated.
                   An octet string expressed as 'sdd.dd Volts' where:
                   s is the sign ('-' for negative or '+' for positive)
                   d is a decimal digit or blank space for a leading zero.
                   The string 'Not Readable!' indicates that the given monitor
                   is not supported on this system.
                   The string 'No Voltage' indicates that the given monitor
                   does not exist on this system or is powered off."
                   ::= { bladeVoltageThresholdsEntry 68 }

       bladeSensor24VoltHighWarning OBJECT-TYPE
                   SYNTAX  OCTET STRING
                   ACCESS  read-only
                   STATUS  mandatory
                   DESCRIPTION
                   "Voltage warning threshold reading for IPMI blades expressed in Volts(V).
                   If the voltage rises above this value a warning alert/event
                   if enabled will be generated.
                   An octet string expressed as 'sdd.dd Volts' where:
                   s is the sign ('-' for negative or '+' for positive)
                   d is a decimal digit or blank space for a leading zero.
                   The string 'Not Readable!' indicates that the given monitor
                   is not supported on this system.
                   The string 'No Voltage' indicates that the given monitor
                   does not exist on this system or is powered off."
                   ::= { bladeVoltageThresholdsEntry 69 }

       bladeSensor24VoltLowWarning OBJECT-TYPE
                   SYNTAX  OCTET STRING
                   ACCESS  read-only
                   STATUS  mandatory
                   DESCRIPTION
                   "Voltage warning threshold reading for IPMI blades expressed in Volts(V).
                   If the voltage drops below this value a warning alert/event
                   if enabled will be generated.
                   An octet string expressed as 'sdd.dd Volts' where:
                   s is the sign ('-' for negative or '+' for positive)
                   d is a decimal digit or blank space for a leading zero.
                   The string 'Not Readable!' indicates that the given monitor
                   is not supported on this system.
                   The string 'No Voltage' indicates that the given monitor
                   does not exist on this system or is powered off."
                   ::= { bladeVoltageThresholdsEntry 70 }

       bladeSensor25VoltHighWarning OBJECT-TYPE
                   SYNTAX  OCTET STRING
                   ACCESS  read-only
                   STATUS  mandatory
                   DESCRIPTION
                   "Voltage warning threshold reading for IPMI blades expressed in Volts(V).
                   If the voltage rises above this value a warning alert/event
                   if enabled will be generated.
                   An octet string expressed as 'sdd.dd Volts' where:
                   s is the sign ('-' for negative or '+' for positive)
                   d is a decimal digit or blank space for a leading zero.
                   The string 'Not Readable!' indicates that the given monitor
                   is not supported on this system.
                   The string 'No Voltage' indicates that the given monitor
                   does not exist on this system or is powered off."
                   ::= { bladeVoltageThresholdsEntry 71 }

       bladeSensor25VoltLowWarning OBJECT-TYPE
                   SYNTAX  OCTET STRING
                   ACCESS  read-only
                   STATUS  mandatory
                   DESCRIPTION
                   "Voltage warning threshold reading for IPMI blades expressed in Volts(V).
                   If the voltage drops below this value a warning alert/event
                   if enabled will be generated.
                   An octet string expressed as 'sdd.dd Volts' where:
                   s is the sign ('-' for negative or '+' for positive)
                   d is a decimal digit or blank space for a leading zero.
                   The string 'Not Readable!' indicates that the given monitor
                   is not supported on this system.
                   The string 'No Voltage' indicates that the given monitor
                   does not exist on this system or is powered off."
                   ::= { bladeVoltageThresholdsEntry 72 }

       bladeSensor26VoltHighWarning OBJECT-TYPE
                   SYNTAX  OCTET STRING
                   ACCESS  read-only
                   STATUS  mandatory
                   DESCRIPTION
                   "Voltage warning threshold reading for IPMI blades expressed in Volts(V).
                   If the voltage rises above this value a warning alert/event
                   if enabled will be generated.
                   An octet string expressed as 'sdd.dd Volts' where:
                   s is the sign ('-' for negative or '+' for positive)
                   d is a decimal digit or blank space for a leading zero.
                   The string 'Not Readable!' indicates that the given monitor
                   is not supported on this system.
                   The string 'No Voltage' indicates that the given monitor
                   does not exist on this system or is powered off."
                   ::= { bladeVoltageThresholdsEntry 73 }

       bladeSensor26VoltLowWarning OBJECT-TYPE
                   SYNTAX  OCTET STRING
                   ACCESS  read-only
                   STATUS  mandatory
                   DESCRIPTION
                   "Voltage warning threshold reading for IPMI blades expressed in Volts(V).
                   If the voltage drops below this value a warning alert/event
                   if enabled will be generated.
                   An octet string expressed as 'sdd.dd Volts' where:
                   s is the sign ('-' for negative or '+' for positive)
                   d is a decimal digit or blank space for a leading zero.
                   The string 'Not Readable!' indicates that the given monitor
                   is not supported on this system.
                   The string 'No Voltage' indicates that the given monitor
                   does not exist on this system or is powered off."
                   ::= { bladeVoltageThresholdsEntry 74 }

       bladeSensor27VoltHighWarning OBJECT-TYPE
                   SYNTAX  OCTET STRING
                   ACCESS  read-only
                   STATUS  mandatory
                   DESCRIPTION
                   "Voltage warning threshold reading for IPMI blades expressed in Volts(V).
                   If the voltage rises above this value a warning alert/event
                   if enabled will be generated.
                   An octet string expressed as 'sdd.dd Volts' where:
                   s is the sign ('-' for negative or '+' for positive)
                   d is a decimal digit or blank space for a leading zero.
                   The string 'Not Readable!' indicates that the given monitor
                   is not supported on this system.
                   The string 'No Voltage' indicates that the given monitor
                   does not exist on this system or is powered off."
                   ::= { bladeVoltageThresholdsEntry 75 }

       bladeSensor27VoltLowWarning OBJECT-TYPE
                   SYNTAX  OCTET STRING
                   ACCESS  read-only
                   STATUS  mandatory
                   DESCRIPTION
                   "Voltage warning threshold reading for IPMI blades expressed in Volts(V).
                   If the voltage drops below this value a warning alert/event
                   if enabled will be generated.
                   An octet string expressed as 'sdd.dd Volts' where:
                   s is the sign ('-' for negative or '+' for positive)
                   d is a decimal digit or blank space for a leading zero.
                   The string 'Not Readable!' indicates that the given monitor
                   is not supported on this system.
                   The string 'No Voltage' indicates that the given monitor
                   does not exist on this system or is powered off."
                   ::= { bladeVoltageThresholdsEntry 76 }

       bladeSensor28VoltHighWarning OBJECT-TYPE
                   SYNTAX  OCTET STRING
                   ACCESS  read-only
                   STATUS  mandatory
                   DESCRIPTION
                   "Voltage warning threshold reading for IPMI blades expressed in Volts(V).
                   If the voltage rises above this value a warning alert/event
                   if enabled will be generated.
                   An octet string expressed as 'sdd.dd Volts' where:
                   s is the sign ('-' for negative or '+' for positive)
                   d is a decimal digit or blank space for a leading zero.
                   The string 'Not Readable!' indicates that the given monitor
                   is not supported on this system.
                   The string 'No Voltage' indicates that the given monitor
                   does not exist on this system or is powered off."
                   ::= { bladeVoltageThresholdsEntry 77 }

       bladeSensor28VoltLowWarning OBJECT-TYPE
                   SYNTAX  OCTET STRING
                   ACCESS  read-only
                   STATUS  mandatory
                   DESCRIPTION
                   "Voltage warning threshold reading for IPMI blades expressed in Volts(V).
                   If the voltage drops below this value a warning alert/event
                   if enabled will be generated.
                   An octet string expressed as 'sdd.dd Volts' where:
                   s is the sign ('-' for negative or '+' for positive)
                   d is a decimal digit or blank space for a leading zero.
                   The string 'Not Readable!' indicates that the given monitor
                   is not supported on this system.
                   The string 'No Voltage' indicates that the given monitor
                   does not exist on this system or is powered off."
                   ::= { bladeVoltageThresholdsEntry 78 }

       bladeSensor29VoltHighWarning OBJECT-TYPE
                   SYNTAX  OCTET STRING
                   ACCESS  read-only
                   STATUS  mandatory
                   DESCRIPTION
                   "Voltage warning threshold reading for IPMI blades expressed in Volts(V).
                   If the voltage rises above this value a warning alert/event
                   if enabled will be generated.
                   An octet string expressed as 'sdd.dd Volts' where:
                   s is the sign ('-' for negative or '+' for positive)
                   d is a decimal digit or blank space for a leading zero.
                   The string 'Not Readable!' indicates that the given monitor
                   is not supported on this system.
                   The string 'No Voltage' indicates that the given monitor
                   does not exist on this system or is powered off."
                   ::= { bladeVoltageThresholdsEntry 79 }

       bladeSensor29VoltLowWarning OBJECT-TYPE
                   SYNTAX  OCTET STRING
                   ACCESS  read-only
                   STATUS  mandatory
                   DESCRIPTION
                   "Voltage warning threshold reading for IPMI blades expressed in Volts(V).
                   If the voltage drops below this value a warning alert/event
                   if enabled will be generated.
                   An octet string expressed as 'sdd.dd Volts' where:
                   s is the sign ('-' for negative or '+' for positive)
                   d is a decimal digit or blank space for a leading zero.
                   The string 'Not Readable!' indicates that the given monitor
                   is not supported on this system.
                   The string 'No Voltage' indicates that the given monitor
                   does not exist on this system or is powered off."
                   ::= { bladeVoltageThresholdsEntry 80 }

       bladeSensor30VoltHighWarning OBJECT-TYPE
                   SYNTAX  OCTET STRING
                   ACCESS  read-only
                   STATUS  mandatory
                   DESCRIPTION
                   "Voltage warning threshold reading for IPMI blades expressed in Volts(V).
                   If the voltage rises above this value a warning alert/event
                   if enabled will be generated.
                   An octet string expressed as 'sdd.dd Volts' where:
                   s is the sign ('-' for negative or '+' for positive)
                   d is a decimal digit or blank space for a leading zero.
                   The string 'Not Readable!' indicates that the given monitor
                   is not supported on this system.
                   The string 'No Voltage' indicates that the given monitor
                   does not exist on this system or is powered off."
                   ::= { bladeVoltageThresholdsEntry 81 }

       bladeSensor30VoltLowWarning OBJECT-TYPE
                   SYNTAX  OCTET STRING
                   ACCESS  read-only
                   STATUS  mandatory
                   DESCRIPTION
                   "Voltage warning threshold reading for IPMI blades expressed in Volts(V).
                   If the voltage drops below this value a warning alert/event
                   if enabled will be generated.
                   An octet string expressed as 'sdd.dd Volts' where:
                   s is the sign ('-' for negative or '+' for positive)
                   d is a decimal digit or blank space for a leading zero.
                   The string 'Not Readable!' indicates that the given monitor
                   is not supported on this system.
                   The string 'No Voltage' indicates that the given monitor
                   does not exist on this system or is powered off."
                   ::= { bladeVoltageThresholdsEntry 82 }

      bladePowerRestart OBJECT IDENTIFIER ::= { processorBlade 6 }
       -- blade power/restart control

        bladePowerRestartTable OBJECT-TYPE
                       SYNTAX  SEQUENCE OF BladePowerRestartEntry
                       ACCESS  not-accessible
                       STATUS  mandatory
                       DESCRIPTION
                       "Table of blade remote power control information.
                       Contains power on/off enablement status for each blade."
                       ::= { bladePowerRestart 1 }

         bladePowerRestartEntry OBJECT-TYPE
                       SYNTAX BladePowerRestartEntry
                       ACCESS  not-accessible
                       STATUS  mandatory
                       DESCRIPTION
                       "Blade power restart table entry"
                       INDEX { powerRestartIndex }
                       ::= { bladePowerRestartTable 1 }


         BladePowerRestartEntry ::= SEQUENCE {
                     powerRestartIndex INTEGER,
                     powerRestartBladeId INTEGER,
                     powerRestartBladeExists INTEGER,
                     powerRestartBladePowerState INTEGER,
                     powerRestartBladeHealthState INTEGER,
                     powerRestartBladeName OCTET STRING,
                     powerOnOffBlade INTEGER,
                     restartBlade INTEGER,
                     restartBladeSMP INTEGER,
                     restartBladeNMI INTEGER,
                     restartBladeClearNVRAM INTEGER,
                     restartBladeInvokeDiags INTEGER,
                     restartBladeInvokeDiagsFromDefaultBootList INTEGER
         }

         powerRestartIndex  OBJECT-TYPE
                     SYNTAX  INTEGER
                     ACCESS  read-only
                     STATUS  mandatory
                     DESCRIPTION
                     "Blade power restart table index."
                     ::= { bladePowerRestartEntry 1 }


         powerRestartBladeId  OBJECT-TYPE
                     SYNTAX  INTEGER {
--                         managementModule(0),
                       blade1(1),
                       blade2(2),
                       blade3(3),
                       blade4(4),
                       blade5(5),
                       blade6(6),
                       blade7(7),
                       blade8(8),
                       blade9(9),
                       blade10(10),
                       blade11(11),
                       blade12(12),
                       blade13(13),
                       blade14(14)
                     }
                     ACCESS  read-only
                     STATUS  mandatory
                     DESCRIPTION
                     "The numeric blade ID."
                     ::= { bladePowerRestartEntry 2 }

         powerRestartBladeExists OBJECT-TYPE
                     SYNTAX  INTEGER {
                       false(0),
                       true(1)
                     }
                     ACCESS  read-only
                     STATUS  mandatory
                     DESCRIPTION
                     "Indicates whether the server blade specified exists or not."
                     ::= { bladePowerRestartEntry 3 }

         powerRestartBladePowerState OBJECT-TYPE
                     SYNTAX  INTEGER {
                       off(0),
                       on(1)
                     }
                     ACCESS  read-only
                     STATUS  mandatory
                     DESCRIPTION
                     "Indicates whether the server blade specified is powered on or not."
                     ::= { bladePowerRestartEntry 4 }

         powerRestartBladeHealthState  OBJECT-TYPE
                   SYNTAX  INTEGER {
                     unknown(0),
                     good(1),
                     warning(2),
                     bad(3)
                   }
                   ACCESS  read-only
                   STATUS  mandatory
                   DESCRIPTION
                   "The system health state for the blade server.
                   0 = unknown, 1 = good, 2 = warning, 3 = bad."
                   ::= { bladePowerRestartEntry 5 }

         powerRestartBladeName OBJECT-TYPE
                     SYNTAX  OCTET STRING
                     ACCESS  read-only
                     STATUS  mandatory
                     DESCRIPTION
                     "The name of the blade as a null terminated string."
                     ::= { bladePowerRestartEntry 6 }

         -- 6.3.2 & 6.4.2
         powerOnOffBlade OBJECT-TYPE
                     SYNTAX  INTEGER {
                       off(0),
                       on(1)
                     }
                     ACCESS  read-write
                     STATUS  mandatory
                     DESCRIPTION
                     "Power on or off a specific blade.
                     
                     NOTE: Value returned for the GET command is meaningless 
                     for this MIB."
                     ::= { bladePowerRestartEntry 7 }

         -- 7.2
         restartBlade OBJECT-TYPE
                     SYNTAX  INTEGER {
                       execute(1)
                     }
                     ACCESS  read-write
                     STATUS  mandatory
                     DESCRIPTION
                     "Restart a blade.
                     
                     NOTE: Value returned for the GET command is meaningless
                     for this MIB."
                     ::= { bladePowerRestartEntry 8 }

         -- 7.4
         restartBladeSMP OBJECT-TYPE
                     SYNTAX  INTEGER {
                       execute(1)
                     }
                     ACCESS  read-write
                     STATUS  mandatory
                     DESCRIPTION
                     "Restart a blade's system management processor.
                     
                     NOTE: Value returned for the GET command is meaningless 
                     for this MIB."
                     ::= { bladePowerRestartEntry 9 }

         restartBladeNMI OBJECT-TYPE
                     SYNTAX  INTEGER {
                       execute(1)
                     }
                     ACCESS  read-write
                     STATUS  mandatory
                     DESCRIPTION
                     "Soft reset and initiate a dump on a blade.  This option is not supported
                     on all blades.
                     
                     NOTE: Value returned for the GET command is meaningless 
                     for this MIB."
                     ::= { bladePowerRestartEntry 10 }
         
         restartBladeClearNVRAM OBJECT-TYPE
                     SYNTAX  INTEGER {
                       execute(1)
                     }
                     ACCESS  read-write
                     STATUS  mandatory
                     DESCRIPTION
                     "Restart a blade and set NVRAM to default values.  This option is not 
                     supported on all blades.
                     
                     NOTE: Value returned for the GET command is meaningless 
                     for this MIB."
                     ::= { bladePowerRestartEntry 11 }

         restartBladeInvokeDiags OBJECT-TYPE
                     SYNTAX  INTEGER {
                       execute(1)
                     }
                     ACCESS  read-write
                     STATUS  mandatory
                     DESCRIPTION
                     "Restart a blade and boot into diagnostic mode.  This option is not 
                     supported on all blades.
                     
                     NOTE: Value returned for the GET command is meaningless 
                     for this MIB."
                     ::= { bladePowerRestartEntry 12 }

         restartBladeInvokeDiagsFromDefaultBootList OBJECT-TYPE
                     SYNTAX  INTEGER {
                       execute(1)
                     }
                     ACCESS  read-write
                     STATUS  mandatory
                     DESCRIPTION
                     "Restart a blade and boot into diagnostic mode from Default Boot List
                     as defined on the blade.  This option is not supported on all blades.
                     
                     NOTE: Value returned for the GET command is meaningless 
                     for this MIB."
                     ::= { bladePowerRestartEntry 13 }


      bladeConfiguration OBJECT IDENTIFIER ::= { processorBlade 7 }
       -- blade power/restart control

        bladeConfigurationTable OBJECT-TYPE
                       SYNTAX  SEQUENCE OF BladeConfigurationEntry
                       ACCESS  not-accessible
                       STATUS  mandatory
                       DESCRIPTION
                       "Table of blade remote power control information.
                       Contains power on/off enablement status for each blade."
                       ::= { bladeConfiguration 1 }

         bladeConfigurationEntry OBJECT-TYPE
                       SYNTAX BladeConfigurationEntry
                       ACCESS  not-accessible
                       STATUS  mandatory
                       DESCRIPTION
                       "Blade configuration table entry"
                       INDEX { configurationIndex }
                       ::= { bladeConfigurationTable 1 }


         BladeConfigurationEntry ::= SEQUENCE {
                     configurationIndex INTEGER,
                     configurationBladeId INTEGER,
                     configurationBladeExists INTEGER,
                     configurationBladePowerState INTEGER,
                     configurationBladeName OCTET STRING
         }

         configurationIndex  OBJECT-TYPE
                     SYNTAX  INTEGER
                     ACCESS  read-only
                     STATUS  mandatory
                     DESCRIPTION
                     "Blade configuration table index."
                     ::= { bladeConfigurationEntry 1 }


         configurationBladeId  OBJECT-TYPE
                     SYNTAX  INTEGER {
--                         managementModule(0),
                       blade1(1),
                       blade2(2),
                       blade3(3),
                       blade4(4),
                       blade5(5),
                       blade6(6),
                       blade7(7),
                       blade8(8),
                       blade9(9),
                       blade10(10),
                       blade11(11),
                       blade12(12),
                       blade13(13),
                       blade14(14)
                     }
                     ACCESS  read-only
                     STATUS  mandatory
                     DESCRIPTION
                     "The numeric blade ID."
                     ::= { bladeConfigurationEntry 2 }

         configurationBladeExists OBJECT-TYPE
                     SYNTAX  INTEGER {
                       false(0),
                       true(1)
                     }
                     ACCESS  read-only
                     STATUS  mandatory
                     DESCRIPTION
                     "Indicates whether the server blade specified exists or not."
                     ::= { bladeConfigurationEntry 3 }

         configurationBladePowerState OBJECT-TYPE
                     SYNTAX  INTEGER {
                       off(0),
                       on(1)
                     }
                     ACCESS  read-only
                     STATUS  mandatory
                     DESCRIPTION
                     "Indicates whether the server blade specified is powered on or not."
                     ::= { bladeConfigurationEntry 4 }

         configurationBladeName OBJECT-TYPE
                     SYNTAX  OCTET STRING
                     ACCESS  read-write
                     STATUS  mandatory
                     DESCRIPTION
                     "The name of the blade as a null terminated string."
                     ::= { bladeConfigurationEntry 5 }


        -- Power Management Policy Settings
        bladePowerManagementPolicy OBJECT IDENTIFIER ::= { bladeConfiguration 2 }

          powerdomain1Oversubscription OBJECT-TYPE
                     SYNTAX  INTEGER {
                       not-allowed(0),
                       recoverable(1),
                       non-recoverable(2)
                     }
                     ACCESS  read-write
                     STATUS  mandatory
                     DESCRIPTION
                     "Power Management Policy settings for power domain 1."
                     ::= { bladePowerManagementPolicy 1 }

          powerdomain2Oversubscription OBJECT-TYPE
                     SYNTAX  INTEGER {
                       not-allowed(0),
                       recoverable(1),
                       non-recoverable(2)
                     }
                     ACCESS  read-write
                     STATUS  mandatory
                     DESCRIPTION
                     "Power Management Policy settings for power domain 2."
                     ::= { bladePowerManagementPolicy 2 }

          acousticMode OBJECT-TYPE
                     SYNTAX  INTEGER {
                       disabled(0),
                       enabled(1)
                     }
                     ACCESS  read-write
                     STATUS  mandatory
                     DESCRIPTION
                     "Acoustic mode setting for thermal conditions"
                     ::= { bladePowerManagementPolicy 3 }
          
      -- 22.1.8
      bladeIPAddrRangeStart OBJECT-TYPE
                      SYNTAX  IpAddress
                      ACCESS  read-write
                      STATUS  mandatory
                      DESCRIPTION
                      "Configure IP address range for all the blades. 
		      Example: the start IP address range of value 10.1.1.1 will
		      make blade 1 to have IP address 10.1.1.1, blade 2 to have 10.1.1.2
                      and so on."
                      ::= { processorBlade 8 }
                      

      bladeCapacityOnDemand OBJECT IDENTIFIER ::= { processorBlade 9 }

        bladeCapacityOnDemandTable OBJECT-TYPE
                       SYNTAX  SEQUENCE OF BladeCapacityOnDemandEntry
                       ACCESS  not-accessible
                       STATUS  mandatory
                       DESCRIPTION
                       "Table of COD blade." 
                       ::= { bladeCapacityOnDemand 1 }

         bladeCapacityOnDemandEntry OBJECT-TYPE
                       SYNTAX BladeCapacityOnDemandEntry
                       ACCESS  not-accessible
                       STATUS  mandatory
                       DESCRIPTION
                       "Blade COD table entry"
                       INDEX { bladeCapacityOnDemandIndex }
                       ::= { bladeCapacityOnDemandTable 1 }


         BladeCapacityOnDemandEntry ::= SEQUENCE {
                     bladeCapacityOnDemandIndex INTEGER,
                     bladeCapacityOnDemandBladeName OCTET STRING,
                     bladeCapacityOnDemandState INTEGER
         }

         bladeCapacityOnDemandIndex  OBJECT-TYPE
                     SYNTAX  INTEGER
                     ACCESS  read-only
                     STATUS  mandatory
                     DESCRIPTION
                     "Blade configuration table index."
                     ::= { bladeCapacityOnDemandEntry 1 }

         bladeCapacityOnDemandBladeName OBJECT-TYPE
                     SYNTAX  OCTET STRING
                     ACCESS  read-only
                     STATUS  mandatory
                     DESCRIPTION
                     "The name of the blade as a null terminated string."
                     ::= { bladeCapacityOnDemandEntry 2 }

         bladeCapacityOnDemandState  OBJECT-TYPE
                     SYNTAX  INTEGER {
                       none(0),
                       standby(1),
                       active(2)
                     }
                     ACCESS  read-write
                     STATUS  mandatory
                     DESCRIPTION
                     "The state of COD."
                     ::= { bladeCapacityOnDemandEntry 3 }


-- JL BEGIN
-- CIRPAK_MODS
       
      bladeBootCountPowerOnTime OBJECT IDENTIFIER ::= { processorBlade 10 }
       -- blade Count of number of boots for a blade and its Power On Time

        bladeBootCountPowerOnTimeTable OBJECT-TYPE
                       SYNTAX  SEQUENCE OF BladeBootCountPowerOnTimeEntry
                       ACCESS  not-accessible
                       STATUS  mandatory
                       DESCRIPTION
                       "Table per blade of the number of boots for the blade and 
                       the number of seconds the blade has been powered on."
                       ::= { bladeBootCountPowerOnTime 1 }

         bladeBootCountPowerOnTimeEntry OBJECT-TYPE
                       SYNTAX BladeBootCountPowerOnTimeEntry
                       ACCESS  not-accessible
                       STATUS  mandatory
                       DESCRIPTION
                       "The number of boots for the blade and 
                       the number of seconds the blade has been powered on."
                       INDEX { bootCountPowerOnTimeBladeIndex }
                       ::= { bladeBootCountPowerOnTimeTable 1 }


         BladeBootCountPowerOnTimeEntry ::= SEQUENCE {
                   bootCountPowerOnTimeBladeIndex INTEGER,
                   bootCountPowerOnTimeBladeId    INTEGER,
                   bootCountPowerOnTimeBoots      INTEGER,
                   bootCountPowerOnTimeSecs       INTEGER

         }
         
         bootCountPowerOnTimeBladeIndex  OBJECT-TYPE
                     SYNTAX  INTEGER
                     ACCESS  read-only
                     STATUS  mandatory
                     DESCRIPTION
                     "Blade boot count/Power On Time table index."
                     ::= { bladeBootCountPowerOnTimeEntry 1 }
                     
         bootCountPowerOnTimeBladeId  OBJECT-TYPE
                     SYNTAX  INTEGER {
                       blade1(1),
                       blade2(2),
                       blade3(3),
                       blade4(4),
                       blade5(5),
                       blade6(6),
                       blade7(7),
                       blade8(8),
                       blade9(9),
                       blade10(10),
                       blade11(11),
                       blade12(12),
                       blade13(13),
                       blade14(14)
                     }
                     ACCESS  read-only
                     STATUS  mandatory
                     DESCRIPTION
                     "The numeric blade ID."
                     ::= { bladeBootCountPowerOnTimeEntry 2 }
                     
         bootCountPowerOnTimeBoots  OBJECT-TYPE
                     SYNTAX  INTEGER
                     ACCESS  read-write
                     STATUS  mandatory
                     DESCRIPTION
                     "Blade Boot Count. If there is no blade in the
                     given slot then this value is undefined. Writing this
                     value resets the Boot Count to zero."
                     ::= { bladeBootCountPowerOnTimeEntry 3 }
                     
         bootCountPowerOnTimeSecs  OBJECT-TYPE
                     SYNTAX  INTEGER
                     ACCESS  read-write
                     STATUS  mandatory
                     DESCRIPTION
                     "Blade Power On Time in seconds. If there is no blade in
                     the given slot then this value is undefined. Writing this
                     value resets the Power On Time to zero."
                     ::= { bladeBootCountPowerOnTimeEntry 4 }
         
-- CIRPAK_MODS END
-- JL END

      
      -- ********************************************************************************
      -- Blade failover
      -- ********************************************************************************
      -- 22.2
--    mmRedundancy OBJECT IDENTIFIER ::= { bladeCenter 2 }
       -- MM failover feature
--
       -- 22.2.1
--     mmDisableFailover OBJECT-TYPE
--                  SYNTAX  INTEGER {
--                     disabled(0),
--                     enabled(1)
--                   }
--                  ACCESS  read-write
--                  STATUS  mandatory
--                  DESCRIPTION
--                  "Enables or disables the failover feature from one MM to
--                  another in a redundantly populated server blade system.
--                  The data value of 0x01 represents enabled and the data
--                  value of 0x00 is disabled.  When the failover is disabled,
--                  a reset will result in a MM reset.  When the failover is
--                  enabled, a MM reset will result in the redundant MM
--                  becoming prime."
--                  ::= { mmRedundancy 1 }
--

      -- ********************************************************************************
      -- Switch module control and config
      -- ********************************************************************************
      -- 22.3
      switchModule OBJECT IDENTIFIER ::= { bladeCenter 3 }
       -- Server blade switch module control and configuration

       -- ********************************************************************************
       -- Switch module control
       -- ********************************************************************************
       -- 22.3.1
       switchModuleControl OBJECT IDENTIFIER ::= { switchModule 1 }
        -- Server blade switch module control

        smControlTable OBJECT-TYPE
                    SYNTAX  SEQUENCE OF SmControlEntry
                    ACCESS  not-accessible
                    STATUS  mandatory
                    DESCRIPTION
                    "Switch module control table."
                    ::= { switchModuleControl 1 }

         smControlEntry  OBJECT-TYPE
                       SYNTAX SmControlEntry
                       ACCESS  not-accessible
                       STATUS  mandatory
                       DESCRIPTION
                       "Switch module control table entry"
                       INDEX { smControlIndex }
                       ::= { smControlTable 1 }

         SmControlEntry ::= SEQUENCE {
                     smControlIndex INTEGER,
                     switchModuleControlId INTEGER,
                     smPostResultsAvailable INTEGER,
                     smPostResultsValue OCTET STRING,
                     switchModuleMemDiagEnableDisable INTEGER,
                     smCfgCtrlEnableDisable INTEGER,
                     smExtEthPortsEnableDisable INTEGER,
                     switchPingRequest INTEGER,
                     smCfgCtrlOnResetEnableDisable INTEGER,
                     smHealthState INTEGER
         }

         smControlIndex OBJECT-TYPE
                     SYNTAX  INTEGER
                     ACCESS  read-only
                     STATUS  mandatory
                     DESCRIPTION
                     "Switch module control table index."
                     ::= { smControlEntry 1 }

         switchModuleControlId OBJECT-TYPE
                     SYNTAX  INTEGER {
                       module1(1),
                       module2(2),
                       module3(3),
                       module4(4)
                     }
                     ACCESS  read-only
                     STATUS  mandatory
                     DESCRIPTION
                     "The switch module numeric identifier."
                     ::= { smControlEntry 2 }

         -- 22.3.1.7
         smPostResultsAvailable OBJECT-TYPE
                     SYNTAX  INTEGER {
                       false(0),
                       true(1)
                     }
                     ACCESS  read-only
                     STATUS  mandatory
                     DESCRIPTION
                     "Describes whether the switch module POST diagnostic result
                     value contained in the smPostResultsValue is valid."
                     ::= { smControlEntry 3 }

         -- 22.3.1.7
         smPostResultsValue OBJECT-TYPE
                     SYNTAX  OCTET STRING
                     ACCESS  read-only
                     STATUS  mandatory
                     DESCRIPTION
                     "The range of values and meanings are as follows:
                      0x00 - 0x7F  (  0 - 127)  Base internal functions
                      0x80 - 0x9F  (128 - 159)  Internal interface failures
                      0xA0 - 0xAF  (160 - 175)  External interface failures
                      0xB0 - 0xFE  (176 - 254)  Reserved
                      0xFF         (255)        Switch completed POST successfully"
                     ::= { smControlEntry 4 }

         -- 22.3.1.4
         switchModuleMemDiagEnableDisable OBJECT-TYPE
                     SYNTAX  INTEGER {
                       enabled(0),
                       disabled(1)
                     }
                     ACCESS  read-write
                     STATUS  mandatory
                     DESCRIPTION
                     "Switch module memory diagnostics enabled or disabled."
                     ::= { smControlEntry 5 }

         -- 22.3.1.5
         smCfgCtrlEnableDisable OBJECT-TYPE
                     SYNTAX  INTEGER {
                       enabled(0),
                       disabled(1)
                     }
                     ACCESS  read-write
                     STATUS  mandatory
                     DESCRIPTION
                     "Switch module configuration control enabled or disabled."
                     ::= { smControlEntry 6 }

         -- 22.3.1.6
         smExtEthPortsEnableDisable OBJECT-TYPE
                     SYNTAX  INTEGER {
                       disabled(0),
                       enabled(1)
                     }
                     ACCESS  read-write
                     STATUS  mandatory
                     DESCRIPTION
                     "Switch module external ethernet ports enabled or disabled."
                     ::= { smControlEntry 7 }

         -- 22.3.1.8
         switchPingRequest OBJECT-TYPE
                     SYNTAX  INTEGER {
                       execute(1)
                     }
                     ACCESS  read-write
                     STATUS  mandatory
                     DESCRIPTION
                     "Sends a ping to a switch module's current IP address.
                     
                     NOTE: Value returned for the GET command is meaningless 
                     for this MIB."
                     ::= { smControlEntry 8 }

         -- 22.3.1.9
         smCfgCtrlOnResetEnableDisable OBJECT-TYPE
                     SYNTAX  INTEGER {
                       enabled(0),
                       disabled(1)
                     }
                     ACCESS  read-write
                     STATUS  mandatory
                     DESCRIPTION
                     "Switch module configuration control enabled or disabled on resets
                     (default and unsolicited)."
                     ::= { smControlEntry 9 }

         -- 22.3.1.15
         smHealthState OBJECT-TYPE
                     SYNTAX  INTEGER {
                       unknown(0),
                       good(1),
                       warning(2),
                       bad(3)
                     }
                     ACCESS  read-write
                     STATUS  mandatory
                     DESCRIPTION
                     "The health state for the switch module.
                     0 = unknown, 1 = good, 2 = warning, 3 = bad."
                     ::= { smControlEntry 15}


        -- 22.3.1.7
        smPowerRestartTable OBJECT-TYPE
                    SYNTAX  SEQUENCE OF SmPowerRestartEntry
                    ACCESS  not-accessible
                    STATUS  mandatory
                    DESCRIPTION
                    "Switch module power restart table."
                    ::= { switchModuleControl 7 }

         smPowerRestartEntry  OBJECT-TYPE
                       SYNTAX SmPowerRestartEntry
                       ACCESS  not-accessible
                       STATUS  mandatory
                       DESCRIPTION
                       "Switch module power restart table entry"
                       INDEX { smPowerRestartIndex }
                       ::= { smPowerRestartTable 1 }

         SmPowerRestartEntry ::= SEQUENCE {
                     smPowerRestartIndex INTEGER,
                     smPowerRestartId INTEGER,
                     smSwitchExists INTEGER,
                     smSwitchType INTEGER,
                     smMACAddress OCTET STRING,
                     smIPAddress IpAddress,
                     switchModulePowerOnOff INTEGER,
                     smReset INTEGER,
                     smResetToDefault INTEGER,
                     smRestartAndRunStdDiag INTEGER,
                     smRestartAndRunExtDiag INTEGER,
                     smRestartAndRunFullDiag INTEGER
         }

         smPowerRestartIndex OBJECT-TYPE
                     SYNTAX  INTEGER
                     ACCESS  read-only
                     STATUS  mandatory
                     DESCRIPTION
                     "Switch module power restart index."
                     ::= { smPowerRestartEntry 1 }

         smPowerRestartId OBJECT-TYPE
                     SYNTAX  INTEGER {
                       module1(1),
                       module2(2),
                       module3(3),
                       module4(4)
                     }
                     ACCESS  read-only
                     STATUS  mandatory
                     DESCRIPTION
                     "The switch module numeric identifier."
                     ::= { smPowerRestartEntry 2 }

         smSwitchExists OBJECT-TYPE
                     SYNTAX  INTEGER {
                       false(0),
                       true(1)
                     }
                     ACCESS  read-only
                     STATUS  mandatory
                     DESCRIPTION
                     "Indicates whether the switch module specified exists or not."
                     ::= { smPowerRestartEntry 3 }

         smSwitchType OBJECT-TYPE
                     SYNTAX  INTEGER {
                       unknown(0),
                       ethernet(1),
                       fibre(2),
                       opm(3),
                       serialCM(4)
                     }
                     ACCESS  read-only
                     STATUS  mandatory
                     DESCRIPTION
                     "Switch module type."
                     ::= { smPowerRestartEntry 4 }

         smMACAddress OBJECT-TYPE
                     SYNTAX  OCTET STRING
                     ACCESS  read-only
                     STATUS  mandatory
                     DESCRIPTION
                     "Switch module MAC address."
                     ::= { smPowerRestartEntry 5 }

         -- 22.3.2.1.1.1
         smIPAddress OBJECT-TYPE
                     SYNTAX  IpAddress
                     ACCESS  read-only
                     STATUS  mandatory
                     DESCRIPTION
                     "The switch module current IP address."
                     ::= { smPowerRestartEntry 6 }

         -- 22.3.1.1
         switchModulePowerOnOff OBJECT-TYPE
                     SYNTAX  INTEGER {
                       poweroff(0),
                       poweron(1)
                     }
                     ACCESS  read-write
                     STATUS  mandatory
                     DESCRIPTION
                     "Switch module power on or power off.  If powering on a currently
                     powered off switch module, then the switch module will execute a POST.
                     The results of this POST will need to be retrieved using the 'Post Results'
                     command.  Note:  When powering off a currently powered on switch module,
                     a minimum of 1 second is needed to allow the switch to power off
                     before powering back on the switch."
                     ::= { smPowerRestartEntry 7 }

         -- 22.3.1.2
         smReset OBJECT-TYPE
                     SYNTAX  INTEGER {
                       execute(1)
                     }
                     ACCESS  read-write
                     STATUS  mandatory
                     DESCRIPTION
                     "For the case where the switch module is currently powered on, this command
                     will effectively power off and then power on the switch module indicated and
                     cause it to run its POST test.  For the case where the switch module is
                     currently powered off, the command will just power on the switch module.
                     
                     NOTE: Value returned  for the GET command is meaningless for this MIB."
                     ::= { smPowerRestartEntry 8 }

         -- 22.3.1.3
         smResetToDefault OBJECT-TYPE
                     SYNTAX  INTEGER {
                       execute(1)
                     }
                     ACCESS  read-write
                     STATUS  mandatory
                     DESCRIPTION
                     "For the case where the switch module is currently powered on, this command
                     will effectively power off and then power on the switch module indicated and
                     cause it to run its POST test.  For the case where the switch module is
                     currently powered off, the command will just power on the switch module.
                     In both cases, the switch module will reset the configuration to the default
                     values.
                     
                     NOTE: Value returned for the GET command is meaningless for this MIB."
                     ::= { smPowerRestartEntry 9 }

         -- 22.3.1.2
         smRestartAndRunStdDiag OBJECT-TYPE
                     SYNTAX  INTEGER {
                       execute(1)
                     }
                     ACCESS  read-write
                     STATUS  mandatory
                     DESCRIPTION
                     "To power cycle the selected module(s) and then run the standard diagnostic 
                     test package.  
                     
                     NOTE: Value returned for the GET commnad is meaningless for this MIB."
                     ::= { smPowerRestartEntry 10 }

         -- 22.3.1.2.1
         smRestartAndRunExtDiag OBJECT-TYPE
                     SYNTAX  INTEGER {
                       execute(1)
                     }
                     ACCESS  read-write
                     STATUS  mandatory
                     DESCRIPTION
                     "To power cycle the selected module(s) and then run the extended diagnostic 
                     test package. This option is not supported on all I/O modules.
                     
                     NOTE: Value returned for the GET command is meaningless for this MIB."
                     ::= { smPowerRestartEntry 11 }

         -- 22.3.1.2.2
         smRestartAndRunFullDiag OBJECT-TYPE
                     SYNTAX  INTEGER {
                       execute(1)
                     }
                     ACCESS  read-write
                     STATUS  mandatory
                     DESCRIPTION
                     "To power cycle the selected module(s) and then run the full diagnostic test 
                     package. The full diagnostic test package may take over 5 minutes to run. 
                     This option is not supported on all I/O modules.
                     
                     NOTE: Value returned for the GET command is meaningless for this MIB."
                     ::= { smPowerRestartEntry 12 }


       -- ********************************************************************************
       -- Switch module config
       -- ********************************************************************************
       -- 22.3.2
       switchModuleConfig OBJECT IDENTIFIER ::= { switchModule 2 }
        -- Server blade switch module configuration

        -- 22.3.2.1
        switchMgmtNetworkCfg OBJECT IDENTIFIER ::= { switchModuleConfig 1 }
         -- Server blade switch module management network config

         -- 
         -- Current switch module network config
         -- 
         -- 22.3.2.1.1
         switchCurrentNwCfg OBJECT IDENTIFIER ::= { switchMgmtNetworkCfg 1 }
          -- Server blade switch module current network config

          smCurrentIPInfoTable OBJECT-TYPE
                      SYNTAX  SEQUENCE OF SmCurrentIPInfoEntry
                      ACCESS  not-accessible
                      STATUS  mandatory
                      DESCRIPTION
                      "Switch module current IP information."
                      ::= { switchCurrentNwCfg 1 }

           smCurrentIPInfoEntry  OBJECT-TYPE
                         SYNTAX SmCurrentIPInfoEntry
                         ACCESS  not-accessible
                         STATUS  mandatory
                         DESCRIPTION
                         "Switch module current IP table entry"
                         INDEX { smCurrentIPInfoIndex }
                         ::= { smCurrentIPInfoTable 1 }

           SmCurrentIPInfoEntry ::= SEQUENCE {
                       smCurrentIPInfoIndex INTEGER,
                       smCurrentIPInfoId INTEGER,
                       smCurrentIPInfoExists INTEGER,
                       smCurrentIPInfoPowerState INTEGER,
--                     smCurrentIPInfoErrorStatus INTEGER,
                       smCurrentIPAddr IpAddress,
                       smCurrentSubnetMask IpAddress,
                       smCurrentGateway IpAddress,
                       smCurrentIPConfigMethod INTEGER
           }

           smCurrentIPInfoIndex OBJECT-TYPE
                       SYNTAX  INTEGER
                       ACCESS  read-only
                       STATUS  mandatory
                       DESCRIPTION
                       "Switch module current IP info index."
                       ::= { smCurrentIPInfoEntry 1 }

           smCurrentIPInfoId OBJECT-TYPE
                       SYNTAX  INTEGER {
                         module1(1),
                         module2(2),
                         module3(3),
                         module4(4)
                       }
                       ACCESS  read-only
                       STATUS  mandatory
                       DESCRIPTION
                       "The switch module numeric identifier."
                       ::= { smCurrentIPInfoEntry 2 }

           smCurrentIPInfoExists OBJECT-TYPE
                       SYNTAX  INTEGER {
                         false(0),
                         true(1)
                       }
                       ACCESS  read-only
                       STATUS  mandatory
                       DESCRIPTION
                       "Indicates whether the switch module specified exists or not."
                       ::= { smCurrentIPInfoEntry 3 }

           smCurrentIPInfoPowerState OBJECT-TYPE
                       SYNTAX  INTEGER {
                         off(0),
                         on(1)
                       }
                       ACCESS  read-only
                       STATUS  mandatory
                       DESCRIPTION
                       "Indicates whether the switch module specified is powered on or not."
                       ::= { smCurrentIPInfoEntry 4 }

--         smCurrentIPInfoErrorStatus OBJECT-TYPE
--                     SYNTAX  INTEGER {
--                       noerror(0),
--                       warning(1),
--                       error(3)
--                     }
--                     ACCESS  read-only
--                     STATUS  mandatory
--                     DESCRIPTION
--                     "Indicates whether the switch module specified has encountered an
--                     error condition."
--                     ::= { smCurrentIPInfoEntry 5 }

           -- 22.3.2.1.1.1
           smCurrentIPAddr OBJECT-TYPE
                        SYNTAX  IpAddress
                        ACCESS  read-only
                        STATUS  mandatory
                        DESCRIPTION
                        "The switch module current IP address."
                        ::= { smCurrentIPInfoEntry 6 }


           -- 22.3.2.1.1.2
           smCurrentSubnetMask OBJECT-TYPE
                        SYNTAX  IpAddress
                        ACCESS  read-only
                        STATUS  mandatory
                        DESCRIPTION
                        "The switch module current subnet mask."
                        ::= { smCurrentIPInfoEntry 7 }

          -- 22.3.2.1.1.3
          smCurrentGateway OBJECT-TYPE
                       SYNTAX  IpAddress
                       ACCESS  read-only
                       STATUS  mandatory
                       DESCRIPTION
                       "The switch module current IP gateway."
                       ::= { smCurrentIPInfoEntry 8 }

          -- 22.3.2.1.1.4
          smCurrentIPConfigMethod OBJECT-TYPE
                       SYNTAX  INTEGER {
                         unknown(0),
                         static(1),
                         dhcp(2),
                         bootp(3)
                       }
                       ACCESS  read-only
                       STATUS  mandatory
                       DESCRIPTION
                       "The switch module current IP configuration method."
                       ::= { smCurrentIPInfoEntry 9 }


         -- ********************************************************************************
         -- New switch module network config
         -- ********************************************************************************
         -- 22.3.2.1.2
         switchNewNwCfg OBJECT IDENTIFIER ::= { switchMgmtNetworkCfg 2 }
          -- Server blade switch module new network config

          -- 22.3.2.1.2.1
          smNewIPInfoTable OBJECT-TYPE
                      SYNTAX  SEQUENCE OF SmNewIPInfoEntry
                      ACCESS  not-accessible
                      STATUS  mandatory
                      DESCRIPTION
                      "Switch module new IP information."
                      ::= { switchNewNwCfg 1 }

           smNewIPInfoEntry  OBJECT-TYPE
                         SYNTAX SmNewIPInfoEntry
                         ACCESS  not-accessible
                         STATUS  mandatory
                         DESCRIPTION
                         "Switch module new IP configuration information table entry"
                         INDEX { smNewIPInfoIndex }
                         ::= { smNewIPInfoTable 1 }

           SmNewIPInfoEntry ::= SEQUENCE {
                       smNewIPInfoIndex INTEGER,
                       smNewIPInfoId INTEGER,
                       smNewIPInfoExists INTEGER,
                       smNewIPInfoPowerState INTEGER,
                       smNewIPAddr IpAddress,
                       smNewSubnetMask IpAddress,
                       smNewGateway IpAddress,
                       smNewIPConfigMethod INTEGER,
                       smNewIPConfigEnableDisable INTEGER
           }

           smNewIPInfoIndex OBJECT-TYPE
                       SYNTAX  INTEGER
                       ACCESS  read-only
                       STATUS  mandatory
                       DESCRIPTION
                       "Switch module new IP info index."
                       ::= { smNewIPInfoEntry 1 }

           smNewIPInfoId OBJECT-TYPE
                       SYNTAX  INTEGER {
                         module1(1),
                         module2(2),
                         module3(3),
                         module4(4)
                       }
                       ACCESS  read-only
                       STATUS  mandatory
                       DESCRIPTION
                       "The switch module numeric identifier."
                       ::= { smNewIPInfoEntry 2 }

           smNewIPInfoExists OBJECT-TYPE
                       SYNTAX  INTEGER {
                         false(0),
                         true(1)
                       }
                       ACCESS  read-only
                       STATUS  mandatory
                       DESCRIPTION
                       "Indicates whether the switch module specified exists or not."
                       ::= { smNewIPInfoEntry 3 }

           smNewIPInfoPowerState OBJECT-TYPE
                       SYNTAX  INTEGER {
                         off(0),
                         on(1)
                       }
                       ACCESS  read-only
                       STATUS  mandatory
                       DESCRIPTION
                       "Indicates whether the switch module specified is powered on or not."
                       ::= { smNewIPInfoEntry 4 }

--         smNewIPInfoErrorStatus OBJECT-TYPE
--                     SYNTAX  INTEGER {
--                       noerror(0),
--                       warning(1),
--                       error(3)
--                     }
--                     ACCESS  read-only
--                     STATUS  mandatory
--                     DESCRIPTION
--                     "Indicates whether the switch module specified has encountered an
--                     error condition."
--                     ::= { smNewIPInfoEntry 5 }

           -- 22.3.2.1.2.1
           smNewIPAddr OBJECT-TYPE
                        SYNTAX  IpAddress
                        ACCESS  read-write
                        STATUS  mandatory
                        DESCRIPTION
                        "The switch module new IP address.  Before setting this object to a new value, 
                        smNewIpconfigEnabledisable object must first be set to disabled."
                        ::= { smNewIPInfoEntry 6 }


           -- 22.3.2.1.2.2
           smNewSubnetMask OBJECT-TYPE
                        SYNTAX  IpAddress
                        ACCESS  read-write
                        STATUS  mandatory
                        DESCRIPTION
                        "The switch module new subnet mask.  Before setting this object to a new value, 
                        smNewIpconfigEnabledisable object must first be set to disabled."
                        ::= { smNewIPInfoEntry 7 }

           -- 22.3.2.1.2.3
           smNewGateway OBJECT-TYPE
                        SYNTAX  IpAddress
                        ACCESS  read-write
                        STATUS  mandatory
                        DESCRIPTION
                        "The switch module new IP gateway.  Before setting this object to a new value, 
                        smNewIpconfigEnabledisable object must first be set to disabled."
                        ::= { smNewIPInfoEntry 8 }

           -- 22.3.2.1.2.4
           smNewIPConfigMethod OBJECT-TYPE
                        SYNTAX  INTEGER {
                          unknown(0),
                          static(1),
                          dhcp(2),
                          bootp(3)
                        }
                        ACCESS  read-write
                        STATUS  mandatory
                        DESCRIPTION
                        "The switch module new IP configuration method.  Before setting this object to a new value, 
                        smNewIpconfigEnabledisable object must first be set to disabled."
                        ::= { smNewIPInfoEntry 9 }

          -- 22.3.2.1.2.5
           smNewIPConfigEnableDisable OBJECT-TYPE
                       SYNTAX  INTEGER {
                         disable(0),
                         enable(1)
                       }
                       ACCESS  read-write
                       STATUS  mandatory
                       DESCRIPTION
                       "A set command enables a new IP configuration that has been
                       previously defined.  A get command indicates whether the new
                       IP configuration information has been enabled."
                       ::= { smNewIPInfoEntry 10 }



    -- 4.5.9
    chassisTopology OBJECT IDENTIFIER ::= { bladeCenter 4 }

     chassisResponseVersion  OBJECT-TYPE
                 SYNTAX  INTEGER
                 ACCESS  read-only
                 STATUS  mandatory
                 DESCRIPTION
                 "Chassis response version."
                 ::= { chassisTopology 1 }

     chassisFlags OBJECT-TYPE
                 SYNTAX  INTEGER {
                   serverBlade(1),
                   rackOrStandAlone(0)
                 }
                 ACCESS  read-only
                 STATUS  mandatory
                 DESCRIPTION
                 "Chassis flags.
                 1 = a server blade chassis, 0 = a rack or standalone chassis."
                 ::= { chassisTopology 2 }

     chassisName OBJECT-TYPE
                 SYNTAX  OCTET STRING
                 ACCESS  read-only
                 STATUS  mandatory
                 DESCRIPTION
                 "The name of the chassis as a null terminated string."
                 ::= { chassisTopology 3 }

     chassisNoOfPBsSupported OBJECT-TYPE
                 SYNTAX  INTEGER
                 ACCESS  read-only
                 STATUS  mandatory
                 DESCRIPTION
                 "Number of processor blades (PBs) supported."
                 ::= { chassisTopology 19 }

     chassisNoOfSMsSupported OBJECT-TYPE
                 SYNTAX  INTEGER
                 ACCESS  read-only
                 STATUS  mandatory
                 DESCRIPTION
                 "Number of switch modules (SMs) supported."
                 ::= { chassisTopology 20 }

     chassisNoOfMMsSupported OBJECT-TYPE
                 SYNTAX  INTEGER
                 ACCESS  read-only
                 STATUS  mandatory
                 DESCRIPTION
                 "Number of management modules (MMs) supported."
                 ::= { chassisTopology 21 }

     chassisNoOfPMsSupported OBJECT-TYPE
                 SYNTAX  INTEGER
                 ACCESS  read-only
                 STATUS  mandatory
                 DESCRIPTION
                 "Number of processor modules (PMs) supported."
                 ::= { chassisTopology 22 }

     chassisNoOfMTsSupported OBJECT-TYPE
                 SYNTAX  INTEGER
                 ACCESS  read-only
                 STATUS  mandatory
                 DESCRIPTION
                 "Number of media trays (MTs) supported."
                 ::= { chassisTopology 23 }

     chassisNoOfBlowersSupported OBJECT-TYPE
                 SYNTAX  INTEGER
                 ACCESS  read-only
                 STATUS  mandatory
                 DESCRIPTION
                 "Number of blowers supported."
                 ::= { chassisTopology 24 }

     chassisPBsInstalled OBJECT-TYPE
                 SYNTAX  OCTET STRING
                 ACCESS  read-only
                 STATUS  mandatory
                 DESCRIPTION
                 "The blades that are installed on the chassis.
                 The blades are listed as a bitmap.  The bitmap is a
                 string containing a list of 1's and 0's that is as long as
                 the number of blades supported.  If a blade is installed in a
                 bay, a 1 is present in the string in the position representing
                 the bay ID as read from left to right.  For example, if blades
                 are installed in bays 1, 5, and 13, and 14 blades are supported,
                 the string would look like '10001000000010'."
                 ::= { chassisTopology 25 }

     chassisSMsInstalled OBJECT-TYPE
                 SYNTAX  OCTET STRING
                 ACCESS  read-only
                 STATUS  mandatory
                 DESCRIPTION
                 "The switch modules that are installed on the chassis.
                 The switch modules are listed as a bitmap.  The bitmap is a
                 string containing a list of 1's and 0's that is as long as
                 the number of switch modules supported.  If a switch module is
                 installed in a bay, a 1 is present in the string in the position
                 representing the bay ID as read from left to right.  For example,
                 if switch modules are installed in bays 1 and 3, and 4 switch modules
                 are supported, the string would look like '1010'."
                 ::= { chassisTopology 29 }

     chassisMMsInstalled OBJECT-TYPE
                 SYNTAX  OCTET STRING
                 ACCESS  read-only
                 STATUS  mandatory
                 DESCRIPTION
                 "The management modules that are installed on the chassis.
                 The management modules are listed as a bitmap.  The bitmap is a
                 string containing a list of 1's and 0's that is as long as the
                 number of management modules supported.  If a management module is installed
                 in a bay, a 1 is present in the string in the position representing
                 the bay ID as read from left to right.  For example, if a management module
                 is installed in bay 1, and 2 management modules are supported, the
                 string would look like '10'."
                 ::= { chassisTopology 30 }

     chassisPMsInstalled OBJECT-TYPE
                 SYNTAX  OCTET STRING
                 ACCESS  read-only
                 STATUS  mandatory
                 DESCRIPTION
                 "The power modules that are installed on the chassis.
                 The power modules are listed as a bitmap.  The bitmap is a
                 string containing a list of 1's and 0's that is as long as
                 the number of power modules supported.  If a power module is
                 installed in a bay, a 1 is present in the string in the position
                 representing the bay ID as read from left to right.  For example,
                 if power modules are installed in bays 1 and 3, and 4 power modules
                 are supported, the string would look like '1010'."
                 ::= { chassisTopology 31 }

     chassisMTInstalled OBJECT-TYPE
                 SYNTAX  INTEGER {
                   no(0),
                   yes(1)
                 }
                 ACCESS  read-only
                 STATUS  mandatory
                 DESCRIPTION
                 "Indicates whether a media tray (MT) is installed."
                 ::= { chassisTopology 32 }

     chassisBlowersInstalled OBJECT-TYPE
                 SYNTAX  OCTET STRING
                 ACCESS  read-only
                 STATUS  mandatory
                 DESCRIPTION
                 "The blowers that are installed on the chassis.
                 The blowers are listed as a bitmap.  The bitmap is a
                 string containing a list of 1's and 0's that is as long as
                 the number of blowers supported.  If a blower is installed in a
                 bay, a 1 is present in the string in the position representing
                 the bay ID as read from left to right.  For example, if a blower
                 is installed in bay 1, and 2 blowers are supported, the string
                 would look like '10'."
                 ::= { chassisTopology 33 }

     chassisActiveMM OBJECT-TYPE
                 SYNTAX  INTEGER
                 ACCESS  read-only
                 STATUS  mandatory
                 DESCRIPTION
                 "The active management module (MM)."
                 ::= { chassisTopology 34 }

     chassisKVMOwner OBJECT-TYPE
                 SYNTAX  INTEGER
                 ACCESS  read-only
                 STATUS  mandatory
                 DESCRIPTION
                 "The blade that currently owns the keyboard/video/monitor (KVM).
                 0 = the KVM devices are owned by the management module."
                 ::= { chassisTopology 35 }

     chassisMediaTrayOwner OBJECT-TYPE
                 SYNTAX  INTEGER
                 ACCESS  read-only
                 STATUS  mandatory
                 DESCRIPTION
                 "The blade that currently owns the media tray.
                 0 = the media tray is owned by the management module."
                 ::= { chassisTopology 36 }

    -- 
    managementModule OBJECT IDENTIFIER ::= { bladeCenter 5 }

      mmStatusTable OBJECT-TYPE
                    SYNTAX  SEQUENCE OF MmStatusEntry
                    ACCESS  not-accessible
                    STATUS  mandatory
                    DESCRIPTION
                    "Table of the management module status.
                    For consistent results, view as a table and not as
                    individual entries."
                    ::= { managementModule 1 }

      mmStatusEntry OBJECT-TYPE
                    SYNTAX MmStatusEntry
                    ACCESS  not-accessible
                    STATUS  mandatory
                    DESCRIPTION
                    "Management module status entry.
                    For consistent results, view as a table and
                    not as individual entries."
                    INDEX { mmStatusIndex }
                    ::= { mmStatusTable 1 }

      MmStatusEntry ::= SEQUENCE {
                  mmStatusIndex INTEGER,
                  mmPresent INTEGER,
                  mmExtIpAddress IpAddress,
                  mmPrimary INTEGER
      }

      mmStatusIndex  OBJECT-TYPE
                  SYNTAX  INTEGER
                  ACCESS  read-only
                  STATUS  mandatory
                  DESCRIPTION
                  "Management module status index."
                  ::= { mmStatusEntry 1 }

      mmPresent  OBJECT-TYPE
                  SYNTAX  INTEGER {
                        no(0),
                        yes(1)
                  }
                  ACCESS  read-only
                  STATUS  mandatory
                  DESCRIPTION
                  "Management module current status."
                  ::= { mmStatusEntry 2 }

      mmExtIpAddress  OBJECT-TYPE
                  SYNTAX  IpAddress
                  ACCESS  read-only
                  STATUS  mandatory
                  DESCRIPTION
                  "Management module external IP address."
                  ::= { mmStatusEntry 3 }

      mmPrimary  OBJECT-TYPE
                  SYNTAX  INTEGER {
                        no(0),
                        yes(1)
                  }
                  ACCESS  read-only
                  STATUS  mandatory
                  DESCRIPTION
                  "Indicate if this Management module is a primary or not."
                  ::= { mmStatusEntry 4 }
                  

    -- ********************************************************************************
    -- Firmware update for MM, Switch modules, and blades
    -- ********************************************************************************
    firmwareUpdate OBJECT IDENTIFIER ::= { bladeCenter 9 }
   
    firmwareUpdateTarget        OBJECT-TYPE
                                SYNTAX  INTEGER {
                                  managementModule(0), 
                                  switchModule1(2), 
                                  switchModule2(3), 
                                  switchModule3(4), 
                                  switchModule4(5), 
                                  blade1(10), 
                                  blade2(11), 
                                  blade3(12),
                                  blade4(13),
                                  blade5(14), 
                                  blade6(15),
                                  blade7(16), 
                                  blade8(17),
                                  blade9(18), 
                                  blade10(19),
                                  blade11(20),
                                  blade12(21),
                                  blade13(22),
                                  blade14(23), 
                                  unknown(255)
                                }  
                                ACCESS  read-write
                                STATUS  mandatory
                                DESCRIPTION
                                "Target module whose firmware will be updated.
                                Note: Some switch modules do not allow firmware update.  
                                When firmware update is attempted on those switch modules, 
                                the agent will report an error."
                                ::= { firmwareUpdate 1 }

    firmwareUpdateTftpServer    OBJECT-TYPE
                                SYNTAX  OCTET STRING (SIZE(0..63))
                                ACCESS  read-write
                                STATUS  mandatory
                                DESCRIPTION
                                "IP address of the TFTP server where the firmware file resides.  
                                The address must be entered in a dotted decimal IP string 
                                (eg. 9.37.44.2)."
                                ::= { firmwareUpdate 2 }
    
    firmwareUpdateFileName      OBJECT-TYPE
                                SYNTAX  OCTET STRING (SIZE(0..63))
                                ACCESS  read-write
                                STATUS  mandatory
                                DESCRIPTION
                                "File name of the firmware file."
                                ::= { firmwareUpdate 3 }
                     
    firmwareUpdateStart         OBJECT-TYPE
                                SYNTAX INTEGER { 
                                  execute(1)
                                }  
                                ACCESS  read-write
                                STATUS  mandatory
                                DESCRIPTION
                                "Start updating the firmware of the specified target module.    
                                Note 1: Depending on the target, it might take up to several 
                                minutes for the flash update to complete.  Do not reset the 
                                target until the control has been returned.  At this point, 
                                the results will be displayed. 
                                Note 2 : Use firmwareUpdateStatus to confirm the status of 
                                the last firmware update initiated by SNMP method.  The 
                                Management Module must be restarted for the new firmware to 
                                take affect.
                                
                                NOTE: Value returned for the GET command is meaningless 
                                for this MIB."
                                ::= { firmwareUpdate 4 }


    firmwareUpdateStatus        OBJECT-TYPE
                                SYNTAX OCTET STRING 
                                ACCESS  read-only
                                STATUS  mandatory
                                DESCRIPTION
                                "Get the status of the last firmware update which was 
                                initiated through SNMP method."
                                ::= { firmwareUpdate 5 }




END
